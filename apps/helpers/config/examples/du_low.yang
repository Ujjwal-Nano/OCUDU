module ocudu-du-low {
  yang-version 1.1;
  namespace "urn:ocudu:du-low";
  prefix du-low;

  description "OCUDU DU-low configuration model.";

  revision 2026-05-11 {
    description "Generated.";
  }

  typedef log-level {
    type enumeration {
      enum "none";
      enum "error";
      enum "warning";
      enum "info";
      enum "debug";
    }
  }

  leaf dryrun {
    type boolean;
    default false;
    description "Enable application dry run mode";
  }
  container log {
    description "Logging configuration";
    leaf filename {
      type string;
      default "/tmp/du_low.log";
      description "Log file output path";
    }
    leaf all-level {
      type log-level;
      default "warning";
      description "Default log level for PHY, MAC, RLC, PDCP, RRC, SDAP, NGAP and GTPU";
    }
    leaf lib-level {
      type log-level;
      default "warning";
      description "Generic log level";
    }
    leaf e2ap-level {
      type log-level;
      default "warning";
      description "E2AP log level (falls back to --all_level if unset)";
    }
    leaf config-level {
      type log-level;
      default "none";
      description "Config log level (falls back to --all_level if unset)";
    }
    leaf hex-max-size {
      type int32 {
        range "-1..1024";
      }
      default 0;
      description "Maximum number of bytes to print in hex (zero for no hex dumps, -1 for unlimited bytes)";
    }
    leaf phy-level {
      type log-level;
      default "warning";
      description "PHY log level (falls back to --all_level if unset)";
    }
    leaf hal-level {
      type log-level;
      default "warning";
      description "HAL log level (falls back to --all_level if unset)";
    }
    leaf broadcast-enabled {
      type boolean;
      default false;
      description "Enable logging in the physical and MAC layer of broadcast messages and all PRACH opportunities";
    }
    leaf phy-rx-symbols-filename {
      type string;
      default "";
      description "Set to a valid file path to print the received symbols.";
    }
    leaf phy-rx-symbols-port {
      type string;
      default "0";
      description "Set to a valid receive port number to dump the IQ symbols from that port only, or set to \"all\" to dump the IQ symbols from all UL receive ports. Only works if \"phy_rx_symbols_filename\" is set. (a non-negative port number or the sentinel \"all\")";
    }
    leaf phy-rx-symbols-prach {
      type boolean;
      default false;
      description "Set to true to dump the IQ symbols from all the PRACH ports. Only works if \"phy_rx_symbols_filename\" is set.";
    }
    leaf ofh-level {
      type log-level;
      default "warning";
      description "Open Fronthaul log level (falls back to --all_level if unset)";
    }
    leaf radio-level {
      type log-level;
      default "info";
      description "Radio log level (falls back to --all_level if unset)";
    }
    leaf fapi-level {
      type log-level;
      default "warning";
      description "FAPI log level (falls back to --all_level if unset)";
    }
  }
  container trace {
    description "General tracer configuration";
    leaf filename {
      type string;
      default "";
      description "Set to a valid file path to enable tracing and write the trace to the file";
    }
    leaf max-tracing-events-per-file {
      type uint32;
      default 1000000;
      description "Maximum number of events per file. Set to zero for no limit";
    }
    leaf nof-tracing-events-after-severe {
      type uint32;
      default 0;
      description "Number of events to write prior to a severe event. Set to zero for writing all events";
    }
    container layers {
      description "Layer basis tracing configuration";
      leaf phy-enable {
        type boolean;
        default false;
        description "Enable tracing for physical layer executors";
      }
    }
  }
  container expert-execution {
    description "Expert execution configuration";
    container affinities {
      description "Application CPU affinities configuration";
      leaf main-pool-cpus {
        type string;
        default "";
        description "CPU cores assigned to main thread pool (comma-separated CPU ids or ranges, e.g. \"0-3,5,7\")";
      }
      leaf main-pool-pinning {
        type string;
        default "mask";
        description "Policy used for assigning CPU cores to the main thread pool (one of: mask, round-robin)";
      }
      container ofh {
        description "Open Fronthaul CPU affinities configuration";
        leaf timing-cpu {
          type string;
          default "";
          description "CPU used for timing in the Radio Unit (comma-separated CPU ids or ranges, e.g. \"0-3,5\")";
        }
      }
    }
    container threads {
      description "Threads configuration";
      container main-pool {
        description "Main thread pool configuration";
        leaf nof-threads {
          type uint32;
          description "Number of threads for processing upper PHY and upper layers.";
        }
        leaf task-queue-size {
          type uint32;
          default 2048;
          description "Main thread pool task queue size.";
        }
        leaf backoff-period {
          type uint32;
          default 50;
          description "Main thread pool back-off period, in microseconds.";
        }
      }
      container upper-phy {
        description "Upper PHY thread configuration";
        leaf pdsch-processor-type {
          type enumeration {
            enum "auto";
            enum "generic";
            enum "flexible";
          }
          default "auto";
          description "PDSCH processor type: auto, generic and flexible.";
        }
        leaf pdsch-cb-batch-length {
          type uint32;
          default 4;
          description "PDSCH flexible processor codeblock-batch size.
Set it to 'auto' to adapt the batch length to the number of threads dedicated to downlink processing,
set it to 'synchronous' to disable batch-splitting and ensure that TB processing remains within the 
calling thread without parallelization. (legal values: a non-negative integer; the sentinel strings \"auto\", \"default\" and \"synchronous\" are not yet supported by the builder API)";
        }
        leaf max-pucch-concurrency {
          type uint32;
          default 0;
          description "Maximum PUCCH processing concurrency for all cells.
Limits the maximum number of threads that can concurrently process Physical Uplink Control Channel
(PUCCH). Set it to zero for no limit of threads.";
        }
        leaf max-pusch-and-srs-concurrency {
          type uint32;
          default 4;
          description "Maximum PUSCH and SRS processing concurrency for all cells.
Limits the maximum number of threads that can concurrently process Physical Uplink Shared Channel 
(PUSCH) and Sounding Reference Signals (SRS). Set it to zero for no limitation. If hardware 
acceleration is enabled, this parameter is set to the number of the accelerator queues.";
        }
        leaf max-pdsch-concurrency {
          type uint32;
          default 0;
          description "Maximum concurrency level for PDSCH processing for all cells.
Limits the number of threads that can concurrently process Physical Downlink Shared Channel (PDSCH).
Set to zero for no limitation. If hardware acceleration is enabled, this parameter is set to the
number of the accelerator queues.";
        }
      }
      container ofh {
        description "Open Fronthaul thread configuration";
        leaf enable-busy-waiting {
          type boolean;
          default false;
          description "Enable busy waiting of the RU timing worker";
        }
      }
      container lower-phy {
        description "Lower PHY thread configuration";
        leaf execution-profile {
          type enumeration {
            enum "blocking";
            enum "single";
            enum "dual";
            enum "triple";
          }
          default "triple";
          description "Lower physical layer executor profile [single, dual, triple].
 - single: one task worker for all the lower physical layer task executors.
 - dual: two task workers - one for the downlink and one for the uplink.
 - triple: dedicated task workers for each of the subtasks (demodulation, reception and transmission).";
        }
      }
    }
    list cell-affinities {
      // WARNING: no key designated; YANG list requires `key`. Use .key("...") at declaration.
      description "Sets the cell CPU affinities configuration on a per cell basis";
      leaf ru-cpus {
        type string;
        default "";
        description "CPU cores used for the Radio Unit tasks (comma-separated CPU ids or ranges, e.g. \"0-3,5\")";
      }
      leaf ru-pinning {
        type string;
        default "mask";
        description "Policy used for assigning CPU cores to the Radio Unit tasks (one of: mask, round-robin)";
      }
    }
    list cell-affinities {
      // WARNING: no key designated; YANG list requires `key`. Use .key("...") at declaration.
      description "Sets the cell CPU affinities configuration on a per cell basis";
      leaf ru-cpus {
        type string;
        default "";
        description "CPU cores used for the Radio Unit tasks (comma-separated CPU ids or ranges, e.g. \"0-3,5\")";
      }
      leaf ru-pinning {
        type string;
        default "mask";
        description "Policy used for assigning CPU cores to the Radio Unit tasks (one of: mask, round-robin)";
      }
    }
  }
  container metrics {
    description "Metrics configuration";
    container layers {
      description "Layer basis metrics configuration";
      leaf enable-executor {
        type boolean;
        default false;
        description "Whether to log application executors metrics";
      }
      leaf enable-app-usage {
        type boolean;
        default false;
        description "Enable application usage metrics";
      }
      leaf enable-du-low {
        type boolean;
        default false;
        description "Enable DU low metrics (upper physical layer)";
      }
      leaf enable-ru {
        type boolean;
        default false;
        description "Enable Radio Unit metrics";
      }
    }
    container periodicity {
      description "Metrics periodicity configuration";
      leaf executors-report-period {
        type int64 {
          range "0..10485760";
        }
        default 1000;
        description "Executors metrics report period in milliseconds";
      }
      leaf app-usage-report-period {
        type uint32;
        default 1000;
        description "Application resource usage metrics report period (in milliseconds)";
      }
      leaf du-report-period {
        type uint32 {
          range "0..10485760";
        }
        default 1000;
        description "DU statistics report period in milliseconds";
      }
    }
    leaf enable-json {
      type boolean;
      default false;
      description "Enable JSON metrics reporting";
    }
    leaf enable-log {
      type boolean;
      default false;
      description "Enable log metrics reporting";
    }
    leaf enable-verbose {
      type boolean;
      default false;
      description "Enable extended detail metrics reporting";
    }
  }
  container remote-control {
    description "Remote control configuration";
    leaf enabled {
      type boolean;
      default false;
      description "Enables the Remote Control Server";
    }
    leaf bind-addr {
      type string;
      default "127.0.0.1";
      description "Remote Control Server bind address";
    }
    leaf port {
      type uint16 {
        range "0..65535";
      }
      default 8001;
      description "Port where the remote control server listens for incoming connections";
    }
  }
  container expert-phy {
    description "Expert physical layer configuration";
    leaf max-proc-delay {
      type uint32 {
        range "1..30";
      }
      default 5;
      description "Maximum allowed DL processing delay in slots.";
    }
    leaf pusch-dec-max-iterations {
      type uint32;
      default 6;
      description "Maximum number of PUSCH LDPC decoder iterations";
    }
    leaf pusch-dec-enable-early-stop {
      type boolean;
      default true;
      description "Enables PUSCH LDPC decoder early stop";
    }
    leaf pusch-decoder-force-decoding {
      type boolean;
      default false;
      description "Forces PUSCH LDPC decoder to decode always";
    }
    leaf pusch-sinr-calc-method {
      type enumeration {
        enum "channel_estimator";
        enum "post_equalization";
        enum "evm";
      }
      default "post_equalization";
      description "PUSCH SINR calculation method: channel_estimator, post_equalization and evm.";
    }
    leaf pusch-channel-estimator-fd-strategy {
      type enumeration {
        enum "filter";
        enum "mean";
        enum "none";
      }
      default "filter";
      description "PUSCH channel estimator frequency-domain smoothing strategy: filter, mean and none.";
    }
    leaf pusch-channel-estimator-td-strategy {
      type enumeration {
        enum "average";
        enum "interpolate";
      }
      default "average";
      description "PUSCH channel estimator time-domain strategy: average and interpolate.";
    }
    leaf pusch-channel-estimator-cfo-compensation {
      type boolean;
      default true;
      description "PUSCH channel estimator CFO compensation.";
    }
    leaf pusch-channel-equalizer-algorithm {
      type enumeration {
        enum "zf";
        enum "mmse";
      }
      default "zf";
      description "PUSCH channel equalizer algorithm: zf and mmse.";
    }
    leaf max-request-headroom-slots {
      type uint32 {
        range "0..30";
      }
      default 0;
      description "Maximum request headroom size in slots.";
    }
    leaf allow-request-on-empty-uplink-slot {
      type boolean;
      default false;
      description "Generates an uplink request in an uplink slot with no PUCCH/PUSCH/SRS PDUs";
    }
    leaf enable-phy-tap {
      type boolean;
      default false;
      description "Enables or disables the PHY tap plugin if it is present while building the application.";
    }
    leaf phy-tap-arguments {
      type string;
      default "";
      description "PHY tap plugin argument string passed during construction.";
    }
  }
  container ru-ofh {
    description "Open Fronthaul Radio Unit configuration";
    leaf gps-alpha {
      type uint32 {
        range "0..12288000";
      }
      default 0;
      description "GPS Alpha";
    }
    leaf gps-beta {
      type int32 {
        range "-32768..32767";
      }
      default 0;
      description "GPS Beta";
    }
    container base-cell {
      description "Base cell parameters that propagate to each entry in --cells";
      leaf t1a-max-cp-dl {
        type int64 {
          range "0..1960";
        }
        default 500;
        description "T1a maximum value for downlink Control-Plane";
      }
      leaf t1a-min-cp-dl {
        type int64 {
          range "0..1960";
        }
        default 258;
        description "T1a minimum value for downlink Control-Plane";
      }
      leaf t1a-max-cp-ul {
        type int64 {
          range "0..1960";
        }
        default 500;
        description "T1a maximum value for uplink Control-Plane";
      }
      leaf t1a-min-cp-ul {
        type int64 {
          range "0..1960";
        }
        default 285;
        description "T1a minimum value for uplink Control-Plane";
      }
      leaf t1a-max-up {
        type int64 {
          range "0..1960";
        }
        default 300;
        description "T1a maximum value for User-Plane";
      }
      leaf t1a-min-up {
        type int64 {
          range "0..1960";
        }
        default 85;
        description "T1a minimum value for User-Plane";
      }
      leaf ta4-max {
        type int64 {
          range "0..1960";
        }
        default 500;
        description "Ta4 maximum value for User-Plane";
      }
      leaf ta4-min {
        type int64 {
          range "0..1960";
        }
        default 85;
        description "Ta4 minimum value for User-Plane";
      }
      leaf is-prach-cp-enabled {
        type boolean;
        default true;
        description "PRACH Control-Plane enabled flag";
      }
      leaf ignore-ecpri-seq-id {
        type boolean;
        default false;
        description "Ignore eCPRI sequence id field value";
      }
      leaf ignore-ecpri-payload-size {
        type boolean;
        default false;
        description "Ignore eCPRI payload size field value";
      }
      leaf ignore-prach-start-symbol {
        type boolean;
        default false;
        description "Ignore the start symbol field in the PRACH U-Plane packets";
      }
      leaf log-lates-as-warnings {
        type boolean;
        default true;
        description "Log late events as warnings";
      }
      leaf warn-unreceived-ru-frames {
        type enumeration {
          enum "never";
          enum "always";
          enum "after_traffic_detection";
        }
        default "after_traffic_detection";
        description "Warn of unreceived Radio Unit frames";
      }
      leaf compr-method-ul {
        type enumeration {
          enum "none";
          enum "bfp";
          enum "bfp selective";
          enum "block scaling";
          enum "mu law";
          enum "modulation";
          enum "modulation selective";
        }
        default "bfp";
        description "Uplink compression method";
      }
      leaf compr-bitwidth-ul {
        type uint32 {
          range "1..16";
        }
        default 9;
        description "Uplink compression bit width";
      }
      leaf compr-method-dl {
        type enumeration {
          enum "none";
          enum "bfp";
          enum "bfp selective";
          enum "block scaling";
          enum "mu law";
          enum "modulation";
          enum "modulation selective";
        }
        default "bfp";
        description "Downlink compression method";
      }
      leaf compr-bitwidth-dl {
        type uint32 {
          range "1..16";
        }
        default 9;
        description "Downlink compression bit width";
      }
      leaf compr-method-prach {
        type enumeration {
          enum "none";
          enum "bfp";
          enum "bfp selective";
          enum "block scaling";
          enum "mu law";
          enum "modulation";
          enum "modulation selective";
        }
        default "bfp";
        description "PRACH compression method";
      }
      leaf compr-bitwidth-prach {
        type uint32 {
          range "1..16";
        }
        default 9;
        description "PRACH compression bit width";
      }
      leaf enable-ul-static-compr-hdr {
        type boolean;
        default true;
        description "Uplink static compression header enabled flag";
      }
      leaf enable-dl-static-compr-hdr {
        type boolean;
        default true;
        description "Downlink static compression header enabled flag";
      }
    }
    list cells {
      // WARNING: no key designated; YANG list requires `key`. Use .key("...") at declaration.
      description "Sets the cell configuration on a per cell basis, overwriting the default configuration defined by cell_cfg";
      leaf t1a-max-cp-dl {
        type int64 {
          range "0..1960";
        }
        default 500;
        description "T1a maximum value for downlink Control-Plane";
      }
      leaf t1a-min-cp-dl {
        type int64 {
          range "0..1960";
        }
        default 258;
        description "T1a minimum value for downlink Control-Plane";
      }
      leaf t1a-max-cp-ul {
        type int64 {
          range "0..1960";
        }
        default 500;
        description "T1a maximum value for uplink Control-Plane";
      }
      leaf t1a-min-cp-ul {
        type int64 {
          range "0..1960";
        }
        default 285;
        description "T1a minimum value for uplink Control-Plane";
      }
      leaf t1a-max-up {
        type int64 {
          range "0..1960";
        }
        default 300;
        description "T1a maximum value for User-Plane";
      }
      leaf t1a-min-up {
        type int64 {
          range "0..1960";
        }
        default 85;
        description "T1a minimum value for User-Plane";
      }
      leaf ta4-max {
        type int64 {
          range "0..1960";
        }
        default 500;
        description "Ta4 maximum value for User-Plane";
      }
      leaf ta4-min {
        type int64 {
          range "0..1960";
        }
        default 85;
        description "Ta4 minimum value for User-Plane";
      }
      leaf is-prach-cp-enabled {
        type boolean;
        default true;
        description "PRACH Control-Plane enabled flag";
      }
      leaf ignore-ecpri-seq-id {
        type boolean;
        default false;
        description "Ignore eCPRI sequence id field value";
      }
      leaf ignore-ecpri-payload-size {
        type boolean;
        default false;
        description "Ignore eCPRI payload size field value";
      }
      leaf ignore-prach-start-symbol {
        type boolean;
        default false;
        description "Ignore the start symbol field in the PRACH U-Plane packets";
      }
      leaf log-lates-as-warnings {
        type boolean;
        default true;
        description "Log late events as warnings";
      }
      leaf warn-unreceived-ru-frames {
        type enumeration {
          enum "never";
          enum "always";
          enum "after_traffic_detection";
        }
        default "after_traffic_detection";
        description "Warn of unreceived Radio Unit frames";
      }
      leaf compr-method-ul {
        type enumeration {
          enum "none";
          enum "bfp";
          enum "bfp selective";
          enum "block scaling";
          enum "mu law";
          enum "modulation";
          enum "modulation selective";
        }
        default "bfp";
        description "Uplink compression method";
      }
      leaf compr-bitwidth-ul {
        type uint32 {
          range "1..16";
        }
        default 9;
        description "Uplink compression bit width";
      }
      leaf compr-method-dl {
        type enumeration {
          enum "none";
          enum "bfp";
          enum "bfp selective";
          enum "block scaling";
          enum "mu law";
          enum "modulation";
          enum "modulation selective";
        }
        default "bfp";
        description "Downlink compression method";
      }
      leaf compr-bitwidth-dl {
        type uint32 {
          range "1..16";
        }
        default 9;
        description "Downlink compression bit width";
      }
      leaf compr-method-prach {
        type enumeration {
          enum "none";
          enum "bfp";
          enum "bfp selective";
          enum "block scaling";
          enum "mu law";
          enum "modulation";
          enum "modulation selective";
        }
        default "bfp";
        description "PRACH compression method";
      }
      leaf compr-bitwidth-prach {
        type uint32 {
          range "1..16";
        }
        default 9;
        description "PRACH compression bit width";
      }
      leaf enable-ul-static-compr-hdr {
        type boolean;
        default true;
        description "Uplink static compression header enabled flag";
      }
      leaf enable-dl-static-compr-hdr {
        type boolean;
        default true;
        description "Downlink static compression header enabled flag";
      }
      leaf network-interface {
        type string;
        default "enp1s0f0";
        description "Network interface name for raw sockets. PCIe (or other bus) port identifier when using DPDK";
      }
      leaf enable-promiscuous {
        type boolean;
        default false;
        description "Promiscuous mode flag";
      }
      leaf check-link-status {
        type boolean;
        default false;
        description "Ethernet link status checking flag";
      }
      leaf ru-mac-addr {
        type string;
        default "70:b3:d5:e1:5b:06";
        description "Radio Unit MAC address";
      }
      leaf du-mac-addr {
        type string;
        default "00:11:22:33:00:77";
        description "Distributed Unit MAC address";
      }
      leaf vlan-tag-cp {
        type uint16 {
          range "1..4094";
        }
        description "C-Plane VLAN identifier";
      }
      leaf vlan-tag-up {
        type uint16 {
          range "1..4094";
        }
        description "U-Plane VLAN identifier";
      }
      leaf vlan-pcp-cp {
        type uint8 {
          range "0..7";
        }
        description "C-Plane VLAN PCP (requires --vlan_tag_cp to be set as well)";
      }
      leaf vlan-pcp-up {
        type uint8 {
          range "0..7";
        }
        description "U-Plane VLAN PCP (requires --vlan_tag_up to be set as well)";
      }
      leaf-list prach-port-id {
        type uint32;
        description "RU PRACH port identifier";
      }
      leaf-list dl-port-id {
        type uint32;
        description "RU downlink port identifier";
      }
      leaf-list ul-port-id {
        type uint32;
        description "RU uplink port identifier";
      }
    }
  }
  container ru-sdr {
    description "SDR Radio Unit configuration";
    leaf srate {
      type decimal64 {
        fraction-digits 6;
      }
      default 61.44;
      description "Sample rate in MHz";
    }
    leaf device-driver {
      type string;
      default "uhd";
      description "Device driver name";
    }
    leaf device-args {
      type string;
      default "";
      description "Optional device arguments";
    }
    leaf tx-gain {
      type decimal64 {
        fraction-digits 6;
      }
      default 50;
      description "Transmit gain in decibels";
    }
    leaf rx-gain {
      type decimal64 {
        fraction-digits 6;
      }
      default 60;
      description "Receive gain in decibels";
    }
    leaf freq-offset {
      type decimal64 {
        fraction-digits 6;
      }
      default 0;
      description "Center frequency offset in hertz";
    }
    leaf clock-ppm {
      type decimal64 {
        fraction-digits 6;
      }
      default 0;
      description "Clock calibration in PPM.";
    }
    leaf lo-offset {
      type decimal64 {
        fraction-digits 6;
      }
      default 0;
      description "LO frequency offset in MHz";
    }
    leaf clock {
      type string;
      default "default";
      description "Clock source";
    }
    leaf sync {
      type string;
      default "default";
      description "Time synchronization source";
    }
    leaf otw-format {
      type string;
      default "default";
      description "Over-the-wire format";
    }
    leaf time-alignment-calibration {
      type string;
      default "auto";
      description "Rx to Tx radio time alignment calibration in samples.
Positive values reduce the RF transmission delay with respect
to the RF reception, while negative values increase it (a signed integer or the sentinel \"auto\" (skip calibration))";
    }
    leaf dl-freq-Hz {
      type decimal64 {
        fraction-digits 6;
      }
      description "Downlink frequency in Hz. If present, it overrides the one derived by DL ARFCN and NR Band.";
    }
    leaf ul-freq-Hz {
      type decimal64 {
        fraction-digits 6;
      }
      description "Uplink frequency in Hz. If present, it overrides the one derived by UL ARFCN and NR Band.";
    }
    container amplitude-control {
      description "Amplitude control parameters";
      leaf tx-gain-backoff {
        type decimal64 {
          fraction-digits 6;
        }
        default 12;
        description "Gain back-off to accommodate the signal PAPR in decibels";
      }
      leaf enable-clipping {
        type boolean;
        default false;
        description "Signal clipping";
      }
      leaf ceiling {
        type decimal64 {
          fraction-digits 6;
        }
        default -0.1;
        description "Clipping ceiling referenced to full scale";
      }
    }
    container expert-cfg {
      description "Generic Radio Unit expert configuration";
      leaf low-phy-dl-throttling {
        type decimal64 {
          fraction-digits 6;
        }
        default 0;
        description "System time-based throttling.
Determines a minimum baseband processor period time between downlink packets. It is expressed as a 
fraction of the time equivalent to the number of samples in the baseband buffer. Set to 0.9 to ensure 
that the downlink packets are processed with a minimum period of 90% of the buffer duration.
Set to zero to disable this feature.";
      }
      leaf tx-mode {
        type enumeration {
          enum "continuous";
          enum "discontinuous";
          enum "same-port";
        }
        default "continuous";
        description "Selects a radio transmission mode. Discontinuous modes are not supported by all radios.
  continuous:    the TX chain is always active.
  discontinuous: the transmitter stops when there is no data to transmit.
  same-port:     the radio transmits and receives from the same antenna port.
";
      }
      leaf power-ramping-time-us {
        type decimal64 {
          fraction-digits 6;
        }
        default 0;
        description "Specifies the power ramping time in microseconds, it proactively initiates the transmission and 
mitigates transient effects.";
      }
    }
  }
  leaf start-time-jitter {
    type uint32 {
      range "0..600";
    }
    default 0;
    description "Start time jitter in milliseconds. A value of 0 disables the start time calculation and the session starts it as soon as possible";
  }
}
