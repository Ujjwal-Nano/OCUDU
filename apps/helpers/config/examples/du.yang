module ocudu-du {
  yang-version 1.1;
  namespace "urn:ocudu:du";
  prefix du;

  description "OCUDU DU configuration model.";

  revision 2026-05-11 {
    description "Generated.";
  }

  typedef log-level {
    type enumeration {
      enum "none";
      enum "error";
      enum "warning";
      enum "info";
      enum "debug";
    }
  }

  grouping sctp-socket {
    leaf sctp-rto-initial {
      type int32;
      default 120;
      description "SCTP initial RTO value in milliseconds (-1 to use system default)";
    }
    leaf sctp-rto-min {
      type int32;
      default 120;
      description "SCTP RTO min in milliseconds (-1 to use system default)";
    }
    leaf sctp-rto-max {
      type int32;
      default 500;
      description "SCTP RTO max in milliseconds (-1 to use system default)";
    }
    leaf sctp-init-max-attempts {
      type int32;
      default 3;
      description "SCTP init max attempts (-1 to use system default)";
    }
    leaf sctp-max-init-timeo {
      type int32;
      default 500;
      description "SCTP max init timeout in milliseconds (-1 to use system default)";
    }
    leaf sctp-hb-interval {
      type int32;
      default 30000;
      description "SCTP heartbeat interval in milliseconds (-1 to use system default)";
    }
    leaf sctp-assoc-max-retx {
      type int32;
      default 10;
      description "SCTP association max retransmissions (-1 to use system default)";
    }
    leaf sctp-nodelay {
      type boolean;
      default false;
      description "Send SCTP messages as soon as possible without any Nagle-like algorithm";
    }
  }

  leaf dryrun {
    type boolean;
    default false;
    description "Enable application dry run mode";
  }
  container log {
    description "Logging configuration";
    leaf filename {
      type string;
      default "/tmp/du.log";
      description "Log file output path";
    }
    leaf all-level {
      type log-level;
      default "warning";
      description "Default log level for PHY, MAC, RLC, PDCP, RRC, SDAP, NGAP and GTPU";
    }
    leaf lib-level {
      type log-level;
      default "warning";
      description "Generic log level";
    }
    leaf e2ap-level {
      type log-level;
      default "warning";
      description "E2AP log level (falls back to --all_level if unset)";
    }
    leaf config-level {
      type log-level;
      default "none";
      description "Config log level (falls back to --all_level if unset)";
    }
    leaf hex-max-size {
      type int32 {
        range "-1..1024";
      }
      default 0;
      description "Maximum number of bytes to print in hex (zero for no hex dumps, -1 for unlimited bytes)";
    }
    leaf mac-level {
      type log-level;
      default "warning";
      description "MAC log level (falls back to --all_level if unset)";
    }
    leaf rlc-level {
      type log-level;
      default "warning";
      description "RLC log level (falls back to --all_level if unset)";
    }
    leaf f1ap-level {
      type log-level;
      default "warning";
      description "F1AP log level (falls back to --all_level if unset)";
    }
    leaf f1u-level {
      type log-level;
      default "warning";
      description "F1-U log level (falls back to --all_level if unset)";
    }
    leaf gtpu-level {
      type log-level;
      default "warning";
      description "GTPU log level (falls back to --all_level if unset)";
    }
    leaf ntn-level {
      type log-level;
      default "warning";
      description "NTN log level (falls back to --all_level if unset)";
    }
    leaf du-level {
      type log-level;
      default "warning";
      description "Log level for the DU (falls back to --all_level if unset)";
    }
    leaf broadcast-enabled {
      type boolean;
      default false;
      description "Enable logging in the physical and MAC layer of broadcast messages and all PRACH opportunities";
    }
    leaf f1ap-json-enabled {
      type boolean;
      default false;
      description "Enable JSON logging of F1AP PDUs";
    }
    leaf high-latency-diagnostics-enabled {
      type boolean;
      default false;
      description "Log performance diagnostics when high computational latencies are detected";
    }
    leaf fapi-level {
      type log-level;
      default "warning";
      description "FAPI log level (falls back to --all_level if unset)";
    }
    leaf phy-level {
      type log-level;
      default "warning";
      description "PHY log level (falls back to --all_level if unset)";
    }
    leaf hal-level {
      type log-level;
      default "warning";
      description "HAL log level (falls back to --all_level if unset)";
    }
    leaf phy-rx-symbols-filename {
      type string;
      default "";
      description "Set to a valid file path to print the received symbols.";
    }
    leaf phy-rx-symbols-port {
      type string;
      default "0";
      description "Set to a valid receive port number to dump the IQ symbols from that port only, or set to \"all\" to dump the IQ symbols from all UL receive ports. Only works if \"phy_rx_symbols_filename\" is set. (a non-negative port number or the sentinel \"all\")";
    }
    leaf phy-rx-symbols-prach {
      type boolean;
      default false;
      description "Set to true to dump the IQ symbols from all the PRACH ports. Only works if \"phy_rx_symbols_filename\" is set.";
    }
    leaf ofh-level {
      type log-level;
      default "warning";
      description "Open Fronthaul log level (falls back to --all_level if unset)";
    }
    leaf radio-level {
      type log-level;
      default "info";
      description "Radio log level (falls back to --all_level if unset)";
    }
  }
  container trace {
    description "General tracer configuration";
    leaf filename {
      type string;
      default "";
      description "Set to a valid file path to enable tracing and write the trace to the file";
    }
    leaf max-tracing-events-per-file {
      type uint32;
      default 1000000;
      description "Maximum number of events per file. Set to zero for no limit";
    }
    leaf nof-tracing-events-after-severe {
      type uint32;
      default 0;
      description "Number of events to write prior to a severe event. Set to zero for writing all events";
    }
    container layers {
      description "Layer basis tracing configuration";
      leaf du-high-enable {
        type boolean;
        default false;
        description "Enable tracing for DU-high executors";
      }
      leaf phy-enable {
        type boolean;
        default false;
        description "Enable tracing for physical layer executors";
      }
    }
  }
  container buffer-pool {
    description "Buffer pool configuration";
    leaf nof-segments {
      type uint64;
      default 1048576;
      description "Number of segments allocated by the buffer pool";
    }
    leaf segment-size {
      type uint64;
      default 2048;
      description "Size of each buffer pool segment in bytes";
    }
  }
  container metrics {
    description "Metrics configuration";
    container layers {
      description "Layer basis metrics configuration";
      leaf enable-app-usage {
        type boolean;
        default false;
        description "Enable application usage metrics";
      }
      leaf enable-sched {
        type boolean;
        default true;
        description "Enable DU scheduler metrics";
      }
      leaf enable-rlc {
        type boolean;
        default false;
        description "Enable RLC metrics";
      }
      leaf enable-mac {
        type boolean;
        default false;
        description "Enable MAC metrics";
      }
      leaf enable-du-proc {
        type boolean;
        default false;
        description "Enable DU management and control procedure metrics";
      }
      leaf enable-du-low {
        type boolean;
        default false;
        description "Enable DU low metrics (upper physical layer)";
      }
      leaf enable-ru {
        type boolean;
        default false;
        description "Enable Radio Unit metrics";
      }
    }
    leaf enable-json {
      type boolean;
      default false;
      description "Enable JSON metrics reporting";
    }
    leaf enable-log {
      type boolean;
      default false;
      description "Enable log metrics reporting";
    }
    leaf enable-verbose {
      type boolean;
      default false;
      description "Enable extended detail metrics reporting";
    }
    leaf autostart-stdout-metrics {
      type boolean;
      default false;
      description "Autostart stdout metrics reporting";
    }
    container periodicity {
      description "Metrics periodicity configuration";
      leaf app-usage-report-period {
        type uint32;
        default 1000;
        description "Application resource usage metrics report period (in milliseconds)";
      }
      leaf du-report-period {
        type uint32 {
          range "0..10485760";
        }
        default 1000;
        description "DU statistics report period in milliseconds";
      }
    }
  }
  container expert-execution {
    description "Expert execution configuration";
    container affinities {
      description "Application CPU affinities configuration";
      leaf main-pool-cpus {
        type string;
        default "";
        description "CPU cores assigned to main thread pool (comma-separated CPU ids or ranges, e.g. \"0-3,5,7\")";
      }
      leaf main-pool-pinning {
        type string;
        default "mask";
        description "Policy used for assigning CPU cores to the main thread pool (one of: mask, round-robin)";
      }
      container ofh {
        description "Open Fronthaul CPU affinities configuration";
        leaf timing-cpu {
          type string;
          default "";
          description "CPU used for timing in the Radio Unit (comma-separated CPU ids or ranges, e.g. \"0-3,5\")";
        }
      }
    }
    container threads {
      description "Threads configuration";
      container main-pool {
        description "Main thread pool configuration";
        leaf nof-threads {
          type uint32;
          description "Number of threads for processing upper PHY and upper layers.";
        }
        leaf task-queue-size {
          type uint32;
          default 2048;
          description "Main thread pool task queue size.";
        }
        leaf backoff-period {
          type uint32;
          default 50;
          description "Main thread pool back-off period, in microseconds.";
        }
      }
      container upper-phy {
        description "Upper PHY thread configuration";
        leaf pdsch-processor-type {
          type enumeration {
            enum "auto";
            enum "generic";
            enum "flexible";
          }
          default "auto";
          description "PDSCH processor type: auto, generic and flexible.";
        }
        leaf pdsch-cb-batch-length {
          type uint32;
          default 4;
          description "PDSCH flexible processor codeblock-batch size.
Set it to 'auto' to adapt the batch length to the number of threads dedicated to downlink processing,
set it to 'synchronous' to disable batch-splitting and ensure that TB processing remains within the 
calling thread without parallelization. (legal values: a non-negative integer; the sentinel strings \"auto\", \"default\" and \"synchronous\" are not yet supported by the builder API)";
        }
        leaf max-pucch-concurrency {
          type uint32;
          default 0;
          description "Maximum PUCCH processing concurrency for all cells.
Limits the maximum number of threads that can concurrently process Physical Uplink Control Channel
(PUCCH). Set it to zero for no limit of threads.";
        }
        leaf max-pusch-and-srs-concurrency {
          type uint32;
          default 4;
          description "Maximum PUSCH and SRS processing concurrency for all cells.
Limits the maximum number of threads that can concurrently process Physical Uplink Shared Channel 
(PUSCH) and Sounding Reference Signals (SRS). Set it to zero for no limitation. If hardware 
acceleration is enabled, this parameter is set to the number of the accelerator queues.";
        }
        leaf max-pdsch-concurrency {
          type uint32;
          default 0;
          description "Maximum concurrency level for PDSCH processing for all cells.
Limits the number of threads that can concurrently process Physical Downlink Shared Channel (PDSCH).
Set to zero for no limitation. If hardware acceleration is enabled, this parameter is set to the
number of the accelerator queues.";
        }
      }
      container ofh {
        description "Open Fronthaul thread configuration";
        leaf enable-busy-waiting {
          type boolean;
          default false;
          description "Enable busy waiting of the RU timing worker";
        }
      }
      container lower-phy {
        description "Lower PHY thread configuration";
        leaf execution-profile {
          type enumeration {
            enum "blocking";
            enum "single";
            enum "dual";
            enum "triple";
          }
          default "triple";
          description "Lower physical layer executor profile [single, dual, triple].
 - single: one task worker for all the lower physical layer task executors.
 - dual: two task workers - one for the downlink and one for the uplink.
 - triple: dedicated task workers for each of the subtasks (demodulation, reception and transmission).";
        }
      }
    }
    container queues {
      description "Task executor queue parameters";
      leaf du-ue-data-executor-queue-size {
        type uint32;
        default 8192;
        description "DU's UE executor task queue size for PDU processing";
      }
    }
    list cell-affinities {
      // WARNING: no key designated; YANG list requires `key`. Use .key("...") at declaration.
      description "Sets the cell CPU affinities configuration on a per cell basis";
      leaf ru-cpus {
        type string;
        default "";
        description "CPU cores used for the Radio Unit tasks (comma-separated CPU ids or ranges, e.g. \"0-3,5\")";
      }
      leaf ru-pinning {
        type string;
        default "mask";
        description "Policy used for assigning CPU cores to the Radio Unit tasks (one of: mask, round-robin)";
      }
    }
    list cell-affinities {
      // WARNING: no key designated; YANG list requires `key`. Use .key("...") at declaration.
      description "Sets the cell CPU affinities configuration on a per cell basis";
      leaf ru-cpus {
        type string;
        default "";
        description "CPU cores used for the Radio Unit tasks (comma-separated CPU ids or ranges, e.g. \"0-3,5\")";
      }
      leaf ru-pinning {
        type string;
        default "mask";
        description "Policy used for assigning CPU cores to the Radio Unit tasks (one of: mask, round-robin)";
      }
    }
    list cell-affinities {
      // WARNING: no key designated; YANG list requires `key`. Use .key("...") at declaration.
      description "Sets the cell CPU affinities configuration on a per cell basis";
      leaf ru-cpus {
        type string;
        default "";
        description "CPU cores used for the Radio Unit tasks (comma-separated CPU ids or ranges, e.g. \"0-3,5\")";
      }
      leaf ru-pinning {
        type string;
        default "mask";
        description "Policy used for assigning CPU cores to the Radio Unit tasks (one of: mask, round-robin)";
      }
    }
  }
  container f1ap {
    description "F1AP interface configuration";
    leaf-list addrs {
      type string;
      description "CU-CP F1-C addresses to connect to. Multiple addresses can be specified for SCTP multi-homing";
    }
    leaf-list bind-addrs {
      type string;
      description "DU F1-C bind addresses. Multiple addresses can be specified for SCTP multi-homing. If left empty, implicit bind is performed";
    }
    uses sctp-socket;
  }
  container f1u {
    description "F1-U interface configuration";
    leaf queue-size {
      type uint32;
      default 2048;
      description "F1-U PDU queue size";
    }
    leaf bind-port {
      type uint16;
      default 2152;
      description "F1-U bind port";
    }
    leaf peer-port {
      type uint16;
      default 2152;
      description "F1-U peer port";
    }
    list socket {
      // WARNING: no key designated; YANG list requires `key`. Use .key("...") at declaration.
      description "Configures UDP/IP socket parameters of the F1-U interface";
      leaf bind-addr {
        type string;
        default "127.0.10.1";
        description "Default local IP address interfaces bind to, unless a specific bind address is specified (must be a valid IPv4 address)";
      }
      leaf sst {
        type uint8 {
          range "0..255";
        }
        description "Slice Service Type";
      }
      leaf sd {
        type uint32 {
          range "0..16777214";
        }
        description "Service Differentiator";
      }
      leaf five-qi {
        type uint16 {
          range "0..255";
        }
        description "Assign this socket to a specific 5QI";
      }
      leaf ext-addr {
        type string;
        default "auto";
        description "External IP address that is advertised for receiving UDP packets. (must be a valid IPv4 address or \"auto\")";
      }
      container udp {
        description "UDP parameters";
        leaf max-rx-msgs {
          type uint32;
          default 256;
          description "Maximum amount of messages RX in a single syscall";
        }
        leaf tx-qsize {
          type uint32;
          default 4096;
          description "Size of TX queue used for batching SDUs.";
        }
        leaf max-tx-msgs {
          type uint32;
          default 256;
          description "Maximum amount of messages TX in a single syscall";
        }
        leaf max-tx-segments {
          type uint32;
          default 256;
          description "Maximum amount of segments TX in a single SDU";
        }
        leaf pool-threshold {
          type decimal64 {
            fraction-digits 6;
          }
          default 0.9;
          description "Pool accupancy threshold after which packets are dropped";
        }
        leaf reuse-addr {
          type boolean;
          default false;
          description "Allow multiple sockets to bind to the same port.";
        }
        leaf dscp {
          type uint32 {
            range "0..63";
          }
          description "Differentiated Services Code Point value.";
        }
      }
    }
  }
  container remote-control {
    description "Remote control configuration";
    leaf enabled {
      type boolean;
      default false;
      description "Enables the Remote Control Server";
    }
    leaf bind-addr {
      type string;
      default "127.0.0.1";
      description "Remote Control Server bind address";
    }
    leaf port {
      type uint16 {
        range "0..65535";
      }
      default 8001;
      description "Port where the remote control server listens for incoming connections";
    }
  }
  leaf gnb-id {
    type uint32;
    default 411;
    description "gNodeB identifier";
  }
  leaf gnb-id-bit-length {
    type uint8 {
      range "22..32";
    }
    default 22;
    description "gNodeB identifier length in bits";
  }
  leaf gnb-du-id {
    type uint64 {
      range "0..68719476735";
    }
    default 0;
    description "gNB-DU Id";
  }
  container pcap {
    description "PCAP configuration";
    leaf f1ap-filename {
      type string;
      default "/tmp/du_f1ap.pcap";
      description "F1AP PCAP file output path";
    }
    leaf f1ap-enable {
      type boolean;
      default false;
      description "Enable F1AP packet capture";
    }
    leaf f1u-filename {
      type string;
      default "/tmp/du_f1u.pcap";
      description "F1-U PCAP file output path";
    }
    leaf f1u-enable {
      type boolean;
      default false;
      description "Enable F1-U packet capture";
    }
    leaf rlc-filename {
      type string;
      default "/tmp/du_rlc.pcap";
      description "RLC PCAP file output path";
    }
    leaf rlc-rb-type {
      type string;
      default "all";
      description "RLC PCAP RB type (all, srb, drb)";
    }
    leaf rlc-enable {
      type boolean;
      default false;
      description "Enable RLC packet capture";
    }
    leaf mac-filename {
      type string;
      default "/tmp/du_mac.pcap";
      description "MAC PCAP file output path";
    }
    leaf mac-type {
      type string;
      default "udp";
      description "MAC PCAP pcap type (dlt or udp)";
    }
    leaf mac-enable {
      type boolean;
      default false;
      description "Enable MAC packet capture";
    }
    leaf e2ap-du-filename {
      type string;
      default "/tmp/du_e2ap.pcap";
      description "E2AP PCAP file output path";
    }
    leaf e2ap-enable {
      type boolean;
      default false;
      description "Enable E2AP packet capture";
    }
  }
  container cell-cfg {
    description "Default cell configuration";
    leaf pci {
      type uint16 {
        range "0..1007";
      }
      default 1;
      description "PCI";
    }
    leaf sector-id {
      type uint32 {
        range "0..16383";
      }
      description "Sector ID (4-14 bits). This value is concatenated with the gNB Id to form the NR Cell Identity (NCI). If not specified, a unique value for the DU is automatically derived";
    }
    leaf dl-arfcn {
      type string;
      default "536020";
      description "Downlink ARFCN (non-negative integer; valid range [0, 3279165])";
    }
    leaf band {
      type int32;
      default auto;
      description "NR band (set to \"auto\" to auto-derive)";
    }
    leaf common-scs {
      type string;
      default "15kHz";
      description "Cell common subcarrier spacing (accepts SCS strings (e.g. \"15kHz\", \"30kHz\"))";
    }
    leaf channel-bandwidth-MHz {
      type int32;
      default 20;
      description "Channel bandwidth in MHz (legal values: {5, 10, 15, 20, 25, 30, 40, 50, 60, 70, 80, 90, 100, 200, 400})";
    }
    leaf nof-antennas-ul {
      type uint32;
      default 1;
      description "Number of antennas in uplink";
    }
    leaf nof-antennas-dl {
      type uint32;
      default 1;
      description "Number of antennas in downlink";
    }
    leaf plmn {
      type string {
        pattern "[0-9]{5,6}";
      }
      default "00101";
      description "PLMN";
    }
    leaf-list additional-plmns {
      type string;
      description "List of PLMNs (each element must be a valid PLMN string)";
    }
    leaf tac {
      type uint32;
      default 7;
      description "TAC (values 0 and 0xfffffe are reserved; value must fit in 24 bits)";
    }
    leaf enabled {
      type boolean;
      default true;
      description "Automatically activate the cell on startup";
    }
    leaf cell-barred {
      type boolean;
      default false;
      description "MIB cellBarred: if true, UEs cannot camp on this cell";
    }
    leaf intra-freq-reselection {
      type boolean;
      default true;
      description "MIB intraFreqReselection: if true, intra-frequency cell reselection is allowed when cell is barred";
    }
    leaf q-rx-lev-min {
      type int32 {
        range "-70..-22";
      }
      default -70;
      description "q-RxLevMin, required minimum received RSRP level for cell selection/re-selection, in dBm";
    }
    leaf q-qual-min {
      type int32 {
        range "-43..-12";
      }
      default -20;
      description "q-QualMin, required minimum received RSRQ level for cell selection/re-selection, in dB";
    }
    leaf pcg-p-nr-fr1 {
      type int32 {
        range "-30..23";
      }
      description "p-nr-fr1, maximum total TX power to be used by the UE in this NR cell group across in FR1";
    }
    container mac-cell-group {
      description "MAC Cell Group parameters";
      container bsr-cfg {
        description "Buffer status report configuration parameters";
        leaf periodic-bsr-timer {
          type uint32;
          default 10;
          description "Periodic Buffer Status Report Timer value in nof. subframes. Value 0 equates to infinity (legal values: {1, 5, 10, 16, 20, 32, 40, 64, 80, 128, 160, 320, 640, 1280, 2560, 0})";
        }
        leaf retx-bsr-timer {
          type uint32;
          default 80;
          description "Retransmission Buffer Status Report Timer value in nof. subframes (legal values: {10, 20, 40, 80, 160, 320, 640, 1280, 2560, 5120, 10240})";
        }
        leaf lc-sr-delay-timer {
          type uint32;
          description "Logical Channel SR delay timer in nof. subframes (legal values: {20, 40, 64, 128, 512, 1024, 2560})";
        }
      }
      container phr-cfg {
        description "Power Headroom report configuration parameters";
        leaf phr-prohibit-timer {
          type uint32;
          default 10;
          description "PHR prohibit timer in nof. subframes (legal values: {0, 10, 20, 50, 100, 200, 500, 1000})";
        }
      }
      container sr-cfg {
        description "Scheduling Request configuration parameters";
        leaf sr-trans-max {
          type uint32;
          default 64;
          description "Maximum number of SR transmissions (legal values: {4, 8, 16, 32, 64})";
        }
        leaf sr-prohibit-timer {
          type uint32;
          description "Timer for SR transmission on PUCCH in ms (legal values: {1, 2, 4, 8, 16, 32, 64, 128})";
        }
      }
    }
    container ssb {
      description "SSB parameters";
      leaf ssb-period {
        type uint32;
        default 10;
        description "Period of SSB scheduling in milliseconds (legal values: {5, 10, 20})";
      }
      leaf ssb-block-power-dbm {
        type int32 {
          range "-60..50";
        }
        default -16;
        description "SS_PBCH_power_block in dBm";
      }
      leaf pss-to-sss-epre {
        type enumeration {
          enum "0";
          enum "3";
        }
        default "0";
        description "SSB PSS to SSS EPRE ratio in dB {0, 3} (legacy CLI11 accepted only the integer values 0 and 3; the builder API maps them to the string keys \"0\" and \"3\".)";
      }
    }
    container sib {
      description "SIB configuration parameters";
      leaf si-window-length {
        type uint32;
        default 160;
        description "The length of the SI scheduling window, in slots. It must be always shorter or equal to the period of the SI message. (legal values: {5, 10, 20, 40, 80, 160, 320, 640, 1280})";
      }
      list si-sched-info {
        // WARNING: no key designated; YANG list requires `key`. Use .key("...") at declaration.
        description "Configures the scheduling for each of the SI-messages broadcast by the gNB";
        leaf si-period {
          type uint32;
          default 32;
          description "SI message scheduling period in radio frames (legal values: {8, 16, 32, 64, 128, 256, 512})";
        }
        leaf-list sib-mapping {
          type uint8;
          description "Mapping of SIB types to SI-messages. SIB numbers should not be repeated (each element must be in {2, 3, 4, 5, 6, 7, 8, 19})";
        }
        leaf si-window-position {
          type uint32 {
            range "1..256";
          }
          description "SI window position of the associated SI-message";
        }
      }
      container sib2 {
        description "SIB2 parameters";
        leaf q-hyst {
          type uint32;
          default 3;
          description "Hysteresis value for ranking criteria. (legal values: {0, 1, 2, 3, 4, 5, 6, 8, 10, 12, 14, 16, 18, 20, 22, 24})";
        }
        leaf thresh-serving-low-p {
          type uint32 {
            range "0..31";
          }
          default 0;
          description "Rx level threshold used by the UE on the serving cell when reselecting towards a lower priority RAT/frequency.";
        }
        leaf cell-reselection-priority {
          type uint32 {
            range "0..7";
          }
          default 6;
          description "Integer part of the cell reselection priority for the frequency of this cell";
        }
        leaf q-rx-lev-min {
          type int32;
          default -140;
          description "Minimum required Rx level in the cell in dBm (must be an even value within [-140, -44])";
        }
        leaf s-intra-search-p {
          type uint32;
          default 62;
          description "Rx level threshold for intra frequency measurements in dB (must be an even value within [0, 62])";
        }
        leaf t-reselection-nr {
          type uint32 {
            range "0..7";
          }
          default 1;
          description "Cell reselection timer value in seconds";
        }
      }
      container sib3 {
        description "SIB3 parameters";
        list intra-freq-neigh-cell-list {
          // WARNING: no key designated; YANG list requires `key`. Use .key("...") at declaration.
          description "Intra frequency neighbor cell list";
          leaf pci {
            type uint16 {
              range "0..1007";
            }
            default 0;
            description "PCI";
          }
          leaf q-offset-cell {
            type int8;
            default 0;
            description "PCI (legal values: {-24, -22, -20, -18, -16, -14, -12, -10, -8, -6, -5, -4, -3, -2, -1, 0, 1, 2, 3, 4, 5, 6, 8, 10, 12, 14, 16, 18, 20, 22, 24})";
          }
        }
        list intra-freq-excluded-cell-list {
          // WARNING: no key designated; YANG list requires `key`. Use .key("...") at declaration.
          description "Intra frequency excluded cell list";
          leaf start {
            type uint16 {
              range "0..1007";
            }
            mandatory true;
            default 0;
            description "Range start";
          }
          leaf size {
            type uint32;
            mandatory true;
            default 1;
            description "Range size (legal values: {1, 4, 8, 12, 16, 24, 32, 48, 64, 84, 96, 128, 168, 252, 504, 1008})";
          }
        }
      }
      container sib4 {
        description "SIB4 parameters";
        list inter-freq-carrier-freq-list {
          // WARNING: no key designated; YANG list requires `key`. Use .key("...") at declaration.
          description "Inter frequency carrier frequency list";
          leaf arfcn {
            type uint32;
            default 0;
            description "ARFCN";
          }
          leaf ssb-scs {
            type string;
            default "15kHz";
            description "SSB subcarrier spacing (accepts SCS strings (e.g. \"15kHz\", \"30kHz\"))";
          }
          leaf derive-ssb-index-from-cell {
            type boolean;
            default false;
            description "Derive SSB index from cell";
          }
          leaf q-rx-lev-min {
            type int32;
            default -140;
            description "Minimum required Rx level in the cell in dBm (must be an even value within [-140, -44])";
          }
          leaf thresh-x-high-p {
            type uint32;
            default 0;
            description "Rx level threshold in dB used when reselecting to a higher priority RAT/frequency in dB (must be an even value within [0, 62])";
          }
          leaf thresh-x-low-p {
            type uint32;
            default 0;
            description "Rx level threshold in dB used when reselecting to a lower priority RAT/frequency in dB (must be an even value within [0, 62])";
          }
          leaf q-offset-freq {
            type int32;
            default 0;
            description "Frequency specific offset in dB for equal priority NR frequencies. (legal values: {-24, -22, -20, -18, -16, -14, -12, -10, -8, -6, -5, -4, -3, -2, -1, 0, 1, 2, 3, 4, 5, 6, 8, 10, 12, 14, 16, 18, 20, 22, 24})";
          }
        }
      }
      container sib5 {
        description "SIB5 parameters";
        leaf t-reselection-eutra {
          type uint32 {
            range "0..7";
          }
          default 0;
          description "Cell reselection timer value in seconds";
        }
        list carrier-freq-list-eutra {
          // WARNING: no key designated; YANG list requires `key`. Use .key("...") at declaration.
          description "EUTRA carrier frequency list";
          leaf earfcn {
            type uint32;
            default 0;
            description "EARFCN";
          }
          leaf allowed-meas-bandwidth {
            type uint32;
            default 0;
            description "Allowed measurement bandwidth (legal values: {6, 15, 25, 50, 75, 100})";
          }
          leaf presence-antenna-port1 {
            type boolean;
            default false;
            description "Whether all neighbor cells use Antenna Port 1";
          }
          leaf cell-reselection-priority {
            type uint32 {
              range "0..7";
            }
            description "Integer part of the cell reselection priority for the frequency of this cell";
          }
          leaf thresh-x-high {
            type uint32;
            default 0;
            description "Rx level threshold in dB used when reselecting to a higher priority RAT/frequency in dB (must be an even value within [0, 62])";
          }
          leaf thresh-x-low {
            type uint32;
            default 0;
            description "Rx level threshold in dB used when reselecting to a lower priority RAT/frequency in dB (must be an even value within [0, 62])";
          }
          leaf q-rx-lev-min {
            type int32;
            default -140;
            description "Minimum required Rx level in the cell in dBm (must be an even value within [-140, -44])";
          }
          leaf q-qual-min {
            type int32 {
              range "-34..-3";
            }
            default -34;
            description "Minimum required quality level in the cell in dB";
          }
          leaf p-max-eutra {
            type int32 {
              range "-30..33";
            }
            default 33;
            description "Maximum allowed transmission power in dBm on the (uplink) carrier frequency.";
          }
        }
      }
      container sib16 {
        description "SIB16 parameters";
        list freq-prio-list-slicing {
          // WARNING: no key designated; YANG list requires `key`. Use .key("...") at declaration.
          description "Frequency priority slicing list entries";
          leaf dl-implicit-carrier-freq {
            type uint32 {
              range "0..8";
            }
            default 0;
            description "DL implicit carrier frequency index for this slicing entry";
          }
          list slice-info-list {
            // WARNING: no key designated; YANG list requires `key`. Use .key("...") at declaration.
            description "Slice info list entries";
            leaf nsag-id {
              type uint32 {
                range "0..255";
              }
              default 0;
              description "NSAG ID";
            }
            leaf allowed {
              type boolean;
              default true;
              description "Whether the list of cells in this slice info is allowed (true) or excluded (false)";
            }
            leaf reselection-priority {
              type decimal64 {
                fraction-digits 6;
              }
              default 0;
              description "Priority associated with this cell reselection slice (must be a multiple of 0.2 within [0.0, 7.8])";
            }
            list cells-allowed {
              // WARNING: no key designated; YANG list requires `key`. Use .key("...") at declaration.
              description "Slice cell list entries";
              leaf start {
                type uint16 {
                  range "0..1007";
                }
                mandatory true;
                default 0;
                description "Range start";
              }
              leaf size {
                type uint32;
                mandatory true;
                default 1;
                description "Range size (legal values: {1, 4, 8, 12, 16, 24, 32, 48, 64, 84, 96, 128, 168, 252, 504, 1008})";
              }
            }
          }
        }
      }
      container etws {
        description "ETWS configuration parameters";
        leaf message-id {
          type uint32 {
            range "0..65535";
          }
          default 4356;
          description "ETWS message ID.";
        }
        leaf serial-num {
          type uint32 {
            range "0..65535";
          }
          default 12288;
          description "ETWS message serial number.";
        }
        leaf warning-type {
          type uint32 {
            range "0..65535";
          }
          default 2432;
          description "ETWS warning type.";
        }
        leaf data-coding-scheme {
          type uint32 {
            range "0..255";
          }
          default 0;
          description "ETWS message CBS coding scheme.";
        }
        leaf warning-message {
          type string;
          description "ETWS warning message. Max. Length and character support depends on the chosen coding scheme.";
        }
      }
      container cmas {
        description "CMAS configuration parameters";
        leaf message-id {
          type uint32 {
            range "0..65535";
          }
          default 4370;
          description "CMAS message ID.";
        }
        leaf serial-num {
          type uint32 {
            range "0..65535";
          }
          default 12291;
          description "CMAS message serial number.";
        }
        leaf data-coding-scheme {
          type uint32 {
            range "0..255";
          }
          default 0;
          description "CMAS message CBS coding scheme.";
        }
        leaf warning-message {
          type string;
          default "";
          description "CMAS warning message. Max. Length and character support depends on the chosen coding scheme.";
        }
      }
      leaf t300 {
        type uint32;
        default 1000;
        description "RRC Connection Establishment timer in ms. The timer starts upon transmission of RRCSetupRequest. (legal values: {100, 200, 300, 400, 600, 1000, 1500, 2000})";
      }
      leaf t301 {
        type uint32;
        default 1000;
        description "RRC Connection Re-establishment timer in ms. The timer starts upon transmission of RRCReestablishmentRequest. (legal values: {100, 200, 300, 400, 600, 1000, 1500, 2000})";
      }
      leaf t310 {
        type uint32;
        default 1000;
        description "Out-of-sync timer in ms. The timer starts upon detecting physical layer problems for the SpCell i.e. upon receiving N310 consecutive out-of-sync indications from lower layers. (legal values: {0, 50, 100, 200, 500, 1000, 2000})";
      }
      leaf n310 {
        type uint32;
        default 1;
        description "Out-of-sync counter. The counter is increased upon reception of \"out-of-sync\" from lower layer while the timer T310 is stopped. Starts the timer T310, when configured value is reached. (legal values: {1, 2, 3, 4, 6, 8, 10, 20})";
      }
      leaf t311 {
        type uint32;
        default 3000;
        description "RRC Connection Re-establishment procedure timer in ms. The timer starts upon initiating the RRC connection re-establishment procedure. (legal values: {1000, 3000, 5000, 10000, 15000, 20000, 30000})";
      }
      leaf n311 {
        type uint32;
        default 1;
        description "In-sync counter. The counter is increased upon reception of the \"in-sync\" from lower layer while the timer T310 is running. Stops the timer T310, when configured value is reached. (legal values: {1, 2, 3, 4, 5, 6, 8, 10})";
      }
      leaf t319 {
        type uint32;
        default 1000;
        description "RRC Connection Resume timer in ms. The timer starts upon transmission of RRCResumeRequest or RRCResumeRequest1. (legal values: {100, 200, 300, 400, 600, 1000, 1500, 2000})";
      }
    }
    container ul-common {
      description "UL common parameters";
      leaf p-max {
        type int32 {
          range "-30..23";
        }
        description "Maximum transmit power allowed in this serving cell";
      }
      leaf max-pucchs-per-slot {
        type uint32 {
          range "1..128";
        }
        default 31;
        description "Maximum number of PUCCH grants that can be allocated per slot";
      }
      leaf max-ul-grants-per-slot {
        type uint32 {
          range "1..144";
        }
        default 32;
        description "Maximum number of UL grants that can be allocated per slot";
      }
      leaf min-pucch-pusch-prb-distance {
        type uint32 {
          range "0..137";
        }
        default 1;
        description "Minimum PRB distance between PUCCH and UE-dedicated PUSCH grants";
      }
    }
    container pdcch {
      description "PDCCH parameters";
      container common {
        description "PDCCH Common configuration parameters";
        leaf coreset0-index {
          type uint32 {
            range "0..15";
          }
          description "CORESET#0 index";
        }
        leaf ss1-n-candidates {
          type string;
          default "[0,0,1,0,0]";
          description "Number of PDCCH candidates per aggregation level for SearchSpace#1. Default: {0, 0, 1, 0, 0} (5-element list of uint8_t (e.g. \"[0,0,1,0,0]\"). Each element must be in {0,1,2,3,4,5,6,8}.) (legacy CLI11 accepted a YAML list of integers; the builder API stores the value as a single string.)";
        }
        leaf ss0-index {
          type uint32 {
            range "0..15";
          }
          default 0;
          description "SearchSpace#0 index";
        }
        leaf max-coreset0-duration {
          type uint8 {
            range "1..2";
          }
          description "Maximum CORESET#0 duration in OFDM symbols to consider when deriving CORESET#0 index";
        }
      }
      container dedicated {
        description "PDCCH Dedicated configuration parameters";
        leaf coreset1-rb-start {
          type uint32 {
            range "0..275";
          }
          description "Starting Common Resource Block (CRB) number for CORESET 1 relative to CRB 0. Default: CRB0";
        }
        leaf coreset1-l-crb {
          type uint32 {
            range "0..275";
          }
          description "Length of CORESET 1 in number of CRBs. Default: Across entire BW of cell";
        }
        leaf coreset1-duration {
          type uint32 {
            range "1..2";
          }
          description "Duration of CORESET 1 in number of OFDM symbols. Default: Max(2, Nof. CORESET#0 symbols)";
        }
        leaf ss2-n-candidates {
          type string;
          default "[0,0,0,0,0]";
          description "Number of PDCCH candidates per aggregation level for SearchSpace#2. Default: {0, 0, 0, 0, 0} i.e. auto-compute nof. candidates (5-element list of uint8_t (e.g. \"[0,0,0,0,0]\"). Each element must be in {0,1,2,3,4,5,6,8}.) (legacy CLI11 accepted a YAML list of integers; the builder API stores the value as a single string.)";
        }
        leaf dci-format-0-1-and-1-1 {
          type boolean;
          default true;
          description "DCI format to use in UE dedicated SearchSpace#2";
        }
        leaf ss2-type {
          type enumeration {
            enum "common";
            enum "ue_dedicated";
          }
          default "ue_dedicated";
          description "SearchSpace type for UE dedicated SearchSpace#2";
        }
        leaf al-cqi-offset {
          type decimal64 {
            fraction-digits 6;
            range "-15..15";
          }
          default 0;
          description "Offset to apply to the CQI value used in the PDCCH aggregation level calculation.";
        }
      }
    }
    container pdsch {
      description "PDSCH parameters";
      leaf min-ue-mcs {
        type uint32 {
          range "0..28";
        }
        default 0;
        description "Minimum UE MCS";
      }
      leaf max-ue-mcs {
        type uint32 {
          range "0..28";
        }
        default 28;
        description "Maximum UE MCS";
      }
      leaf fixed-rar-mcs {
        type uint32 {
          range "0..28";
        }
        default 0;
        description "Fixed RAR MCS";
      }
      leaf fixed-sib1-mcs {
        type uint32 {
          range "0..28";
        }
        default 5;
        description "Fixed SIB1 MCS";
      }
      leaf harq-feedback-disabled {
        type string;
        default "false";
        description "Disable DL HARQ Feedback (only for NTN cells).
If set to true, applies the mask 0x0fffffff and disables HARQ feedback for all except the first four HARQs.
If set to a string, it must be a 32-bit bitmap (0x… or 0b…) of the HARQ processes to disable.
The bit set to 1 indicates HARQ processes with disabled DL HARQ feedback and the bit set to 0,
identify HARQ processes with enabled DL HARQ feedback.The leftmost bit corresponds to HARQ process ID 0; bits for unconfigured HARQ process IDs are ignored.
 (accepts \"true\", \"false\" or a 32-bit bitmap (\"0x...\" / \"0b...\").)";
      }
      leaf nof-harqs {
        type uint32;
        default 16;
        description "Number of DL HARQ processes. The value 32 is applied only for NTN cells when supported by the UE; otherwise, it defaults to 16. (legal values: {2, 4, 6, 8, 10, 12, 16, 32})";
      }
      leaf max-nof-harq-retxs {
        type uint32 {
          range "0..64";
        }
        default 4;
        description "Maximum number of times a DL HARQ can be retransmitted, before it gets discarded.";
      }
      leaf harq-retx-timeout {
        type uint32 {
          range "10..500";
        }
        default 100;
        description "Maximum time, in milliseconds, between a HARQ NACK and the scheduler allocating the respective HARQ for retransmission. If this timeout is exceeded, the HARQ process is discarded.";
      }
      leaf max-consecutive-kos {
        type uint32;
        default 100;
        description "Maximum number of HARQ-ACK consecutive KOs before an Radio Link Failure is reported";
      }
      leaf-list rv-sequence {
        type uint32;
        description "RV sequence for PUSCH. (e.g. [0 2 3 1] (each element must be in {0, 1, 2, 3})";
      }
      leaf mcs-table {
        type enumeration {
          enum "qam64";
          enum "qam256";
          enum "qam64lowse";
        }
        default "qam256";
        description "MCS table to use PDSCH";
      }
      leaf min-rb-size {
        type uint32 {
          range "1..275";
        }
        default 1;
        description "Minimum RB size for UE PDSCH resource allocation";
      }
      leaf max-rb-size {
        type uint32 {
          range "1..275";
        }
        default 275;
        description "Maximum RB size for UE PDSCH resource allocation";
      }
      leaf start-rb {
        type uint32 {
          range "0..275";
        }
        default 0;
        description "Start RB for resource allocation of UE PDSCHs";
      }
      leaf end-rb {
        type uint32 {
          range "0..275";
        }
        default 275;
        description "End RB for resource allocation of UE PDSCHs";
      }
      leaf max-pdschs-per-slot {
        type uint32 {
          range "1..35";
        }
        default 35;
        description "Maximum number of PDSCH grants per slot, including SIB, RAR, Paging and UE data grants.";
      }
      leaf max-alloc-attempts {
        type uint32 {
          range "1..35";
        }
        default 35;
        description "Maximum number of DL or UL PDCCH grant allocation attempts per slot before scheduler skips the slot";
      }
      leaf olla-cqi-inc-step {
        type decimal64 {
          fraction-digits 6;
          range "0..1";
        }
        default 0.001;
        description "Outer-loop link adaptation (OLLA) increment value. The value 0 means that OLLA is disabled";
      }
      leaf olla-target-bler {
        type decimal64 {
          fraction-digits 6;
          range "0..0.5";
        }
        default 0.01;
        description "Target DL BLER set in Outer-loop link adaptation (OLLA) algorithm";
      }
      leaf olla-max-cqi-offset {
        type decimal64 {
          fraction-digits 6;
          range "0..max";
        }
        default 4;
        description "Maximum offset that the Outer-loop link adaptation (OLLA) can apply to CQI";
      }
      leaf dc-offset {
        type string;
        default "center";
        description "Direct Current (DC) Offset in number of subcarriers, using the common SCS as reference for carrier spacing, and the center of the gNB DL carrier as DC offset value 0. The user can additionally set \"outside\" to define that the DC offset falls outside the DL carrier or \"undetermined\" in the case the DC offset is unknown. (accepts an integer in [min,max] or one of {\"outside\",\"undetermined\",\"center\"}.)";
      }
      leaf harq-la-cqi-drop-threshold {
        type uint8 {
          range "0..15";
        }
        default 3;
        description "Link Adaptation (LA) threshold for drop in CQI of the first HARQ transmission above which HARQ retransmissions are cancelled. Set this value to 0 to disable this feature";
      }
      leaf harq-la-ri-drop-threshold {
        type uint8 {
          range "0..4";
        }
        default 1;
        description "Link Adaptation (LA) threshold for drop in nof. layers of the first HARQ transmission above which HARQ retransmission is cancelled. Set this value to 0 to disable this feature";
      }
      leaf dmrs-additional-position {
        type uint32 {
          range "0..3";
        }
        default 2;
        description "PDSCH DMRS additional position";
      }
      leaf interleaving-bundle-size {
        type uint8;
        default 0;
        description "PDSCH interleaving bundle size. Valid values: [0, 2, 4] (legal values: {0, 2, 4})";
      }
      leaf max-rank {
        type uint32 {
          range "0..max";
        }
        description "Maximum number of PDSCH transmission layers. The actual maximum is limited by the number of DL antennas.";
      }
      leaf enable-csi-rs-pdsch-multiplexing {
        type boolean;
        default true;
        description "Enable multiplexing of CSI-RS and PDSCH";
      }
    }
    container pusch {
      description "PUSCH parameters";
      leaf min-ue-mcs {
        type uint32 {
          range "0..28";
        }
        default 0;
        description "Minimum UE MCS";
      }
      leaf max-ue-mcs {
        type uint32 {
          range "0..28";
        }
        default 28;
        description "Maximum UE MCS";
      }
      leaf harq-mode-b {
        type string;
        default "false";
        description "Set HARQ Mode B (only for NTN cells).
If set to true, applies the mask 0x0fffffff to set HARQ Mode B for all except the first four HARQ processes.
If set to a string, it must be a 32-bit bitmap (0x… or 0b…) indicating which HARQ processes use Mode B.
A bit set to 1 indicates HARQ Mode B; a bit set to 0 indicates HARQ Mode A.
The leftmost bit corresponds to HARQ process ID 0; bits for unconfigured HARQ process IDs are ignored.
 (accepts \"true\", \"false\" or a 32-bit bitmap (\"0x...\" / \"0b...\").)";
      }
      leaf nof-harqs {
        type uint32;
        default 16;
        description "Number of UL HARQ processes. The value 32 is applied only for NTN cells when supported by the UE; otherwise, it defaults to 16. (legal values: {16, 32})";
      }
      leaf max-nof-harq-retxs {
        type uint32 {
          range "0..64";
        }
        default 4;
        description "Maximum number of times a UL HARQ can be retransmitted, before it gets discarded.";
      }
      leaf harq-retx-timeout {
        type uint32 {
          range "10..500";
        }
        default 100;
        description "Maximum time, in milliseconds, between a CRC=KO and the scheduler allocating the respective HARQ for retransmission. If this timeout is exceeded, the HARQ process is discarded.";
      }
      leaf max-consecutive-kos {
        type uint32;
        default 100;
        description "Maximum number of CRC consecutive KOs before an Radio Link Failure is reported";
      }
      leaf-list rv-sequence {
        type uint32;
        description "RV sequence for PUSCH. (e.g. [0 2 3 1] (each element must be in {0, 1, 2, 3})";
      }
      leaf mcs-table {
        type enumeration {
          enum "qam64";
          enum "qam256";
          enum "qam64lowse";
        }
        default "qam256";
        description "MCS table to use PUSCH";
      }
      leaf max-rank {
        type uint32 {
          range "1..4";
        }
        default 4;
        description "Maximum number of PUSCH transmission layers. The actual maximum is limited by the number of receive ports and UE capabilities.";
      }
      leaf msg3-delta-preamble {
        type int32 {
          range "-1..6";
        }
        default 6;
        description "msg3-DeltaPreamble, Power offset between msg3 and RACH preamble transmission";
      }
      leaf p0-nominal-with-grant {
        type int32;
        default -76;
        description "P0 value for PUSCH with grant (except msg3). Value in dBm. Valid values must be multiple of 2 and within the [-202, 24] interval.  Default: -76 (must be a multiple of 2 within [-202, 24])";
      }
      leaf msg3-delta-power {
        type int32;
        default 8;
        description "Target power level at the network receiver side, in dBm. Valid values must be multiple of 2 and within the [-6, 8] interval. Default: 8 (must be a multiple of 2 within [-6, 8])";
      }
      leaf max-puschs-per-slot {
        type uint32 {
          range "1..16";
        }
        default 16;
        description "Maximum number of PUSCH grants per slot";
      }
      leaf beta-offset-ack-idx-1 {
        type uint32 {
          range "0..31";
        }
        default 11;
        description "betaOffsetACK-Index1 part of UCI-OnPUSCH";
      }
      leaf beta-offset-ack-idx-2 {
        type uint32 {
          range "0..31";
        }
        default 6;
        description "betaOffsetACK-Index2 part of UCI-OnPUSCH";
      }
      leaf beta-offset-ack-idx-3 {
        type uint32 {
          range "0..31";
        }
        default 4;
        description "betaOffsetACK-Index3 part of UCI-OnPUSCH";
      }
      leaf beta-offset-csi-p1-idx-1 {
        type uint32 {
          range "0..31";
        }
        default 13;
        description "betaOffsetCSI-Part1-Index1 part of UCI-OnPUSCH";
      }
      leaf beta-offset-csi-p1-idx-2 {
        type uint32 {
          range "0..31";
        }
        default 10;
        description "betaOffsetCSI-Part1-Index2 part of UCI-OnPUSCH";
      }
      leaf beta-offset-csi-p2-idx-1 {
        type uint32 {
          range "0..31";
        }
        default 13;
        description "betaOffsetCSI-Part2-Index1 part of UCI-OnPUSCH";
      }
      leaf beta-offset-csi-p2-idx-2 {
        type uint32 {
          range "0..31";
        }
        default 10;
        description "betaOffsetCSI-Part2-Index2 part of UCI-OnPUSCH";
      }
      leaf min-k2 {
        type uint32 {
          range "1..4";
        }
        default 4;
        description "Minimum value of K2 (difference in slots between PDCCH and PUSCH).";
      }
      leaf dc-offset {
        type string;
        default "center";
        description "Direct Current (DC) Offset in number of subcarriers, using the common SCS as reference for carrier spacing, and the center of the gNB UL carrier as DC offset value 0. The user can additionally set \"outside\" to define that the DC offset falls outside the UL carrier or \"undetermined\" in the case the DC offset is unknown. (accepts an integer in [min,max] or one of {\"outside\",\"undetermined\",\"center\"}.)";
      }
      leaf olla-snr-inc-step {
        type decimal64 {
          fraction-digits 6;
          range "0..1";
        }
        default 0.001;
        description "Outer-loop link adaptation (OLLA) increment value. The value 0 means that OLLA is disabled";
      }
      leaf olla-target-bler {
        type decimal64 {
          fraction-digits 6;
          range "0..0.5";
        }
        default 0.01;
        description "Target UL BLER set in Outer-loop link adaptation (OLLA) algorithm";
      }
      leaf olla-max-snr-offset {
        type decimal64 {
          fraction-digits 6;
          range "0..max";
        }
        default 5;
        description "Maximum offset that the Outer-loop link adaptation (OLLA) can apply to the estimated UL SINR";
      }
      leaf dmrs-additional-position {
        type uint32 {
          range "0..3";
        }
        default 2;
        description "PUSCH DMRS additional position";
      }
      leaf min-rb-size {
        type uint32 {
          range "1..275";
        }
        default 1;
        description "Minimum RB size for UE PUSCH resource allocation";
      }
      leaf max-rb-size {
        type uint32 {
          range "1..275";
        }
        default 275;
        description "Maximum RB size for UE PUSCH resource allocation";
      }
      leaf start-rb {
        type uint32 {
          range "0..275";
        }
        default 0;
        description "Start RB for resource allocation of UE PUSCHs";
      }
      leaf end-rb {
        type uint32 {
          range "0..275";
        }
        default 275;
        description "End RB for resource allocation of UE PUSCHs";
      }
      leaf enable-cl-loop-pw-control {
        type boolean;
        default false;
        description "Enable closed-loop power control for PUSCH";
      }
      leaf enable-phr-bw-adaptation {
        type boolean;
        default false;
        description "Enable bandwidth adaptation to prevent negative PHR";
      }
      leaf target-sinr {
        type decimal64 {
          fraction-digits 6;
          range "-5..30";
        }
        default 10;
        description "Target PUSCH SINR in dB";
      }
      leaf ref-path-loss {
        type decimal64 {
          fraction-digits 6;
          range "50..120";
        }
        default 70;
        description "Reference path-loss for target PUSCH SINR in dB";
      }
      leaf pl-compensation-factor {
        type decimal64 {
          fraction-digits 6;
        }
        default 1;
        description "Fractional path-loss compensation factor in PUSCH power control (legal values: {0.4, 0.5, 0.6, 0.7, 0.8, 0.9, 1.0})";
      }
      leaf enable-transform-precoding {
        type boolean;
        default false;
        description "Enable transform precoding for PUSCH.";
      }
    }
    container pucch {
      description "PUCCH parameters";
      leaf p0-nominal {
        type int32;
        default -90;
        description "Power control parameter P0 for PUCCH transmissions. Value in dBm. Valid values must be multiple of 2 and within the [-202, 24] interval. Default: -90 (must be a multiple of 2 within [-202, 24])";
      }
      leaf pucch-resource-common {
        type uint32 {
          range "0..15";
        }
        description "Index of PUCCH resource set for the common configuration";
      }
      leaf sr-period-ms {
        type decimal64 {
          fraction-digits 6;
        }
        default 20;
        description "SR period in msec (legal values: {1, 2, 2.5, 4, 5, 8, 10, 16, 20, 40, 80, 160, 320})";
      }
      leaf formats {
        type enumeration {
          enum "f0_and_f2";
          enum "f1_and_f2";
          enum "f1_and_f3";
          enum "f1_and_f4";
        }
        default "f1_and_f2";
        description "PUCCH formats combination to use. Values: {f0_and_f2, f1_and_f2, f1_and_f3, f1_and_f4}. Default: f1_and_f2";
      }
      leaf resource-set-size {
        type uint32 {
          range "1..8";
        }
        default 8;
        description "Number of PUCCH resources in each PUCCH resource set";
      }
      leaf nof-cell-res-set-configs {
        type uint32 {
          range "1..10";
        }
        default 2;
        description "Number of PUCCH Resource Set configurations that are available per cell. NOTE: the higher the number of configurations, the lower the chances UEs have to share the same PUCCH resources for HARQ-ACK.";
      }
      leaf nof-cell-sr-res {
        type uint32 {
          range "1..100";
        }
        default 8;
        description "Number of PUCCH F0/F1 resources available per cell for SR";
      }
      leaf nof-cell-csi-res {
        type uint32 {
          range "0..100";
        }
        default 8;
        description "Number of PUCCH F2/F3/F4 resources available per cell for CSI";
      }
      leaf f0-intraslot-freq-hop {
        type boolean;
        default false;
        description "Enable intra-slot frequency hopping for PUCCH F0";
      }
      leaf f1-enable-occ {
        type boolean;
        default false;
        description "Enable OCC for PUCCH F1";
      }
      leaf f1-nof-cyclic-shifts {
        type uint32;
        default 2;
        description "Number of possible cyclic shifts available for PUCCH F1 resources (legal values: {1, 2, 3, 4, 6, 12})";
      }
      leaf f1-intraslot-freq-hop {
        type boolean;
        default false;
        description "Enable intra-slot frequency hopping for PUCCH F1";
      }
      leaf f2-max-nof-rbs {
        type uint32 {
          range "1..16";
        }
        default 1;
        description "Max number of RBs for PUCCH F2 resources";
      }
      leaf f2-max-payload {
        type uint32 {
          range "4..40";
        }
        description "Min required payload capacity in bits for PUCCH F2 resources";
      }
      leaf f2-max-code-rate {
        type enumeration {
          enum "dot08";
          enum "dot15";
          enum "dot25";
          enum "dot35";
          enum "dot45";
          enum "dot60";
          enum "dot80";
        }
        default "dot35";
        description "PUCCH F2 max code rate {dot08, dot15, dot25, dot35, dot45, dot60, dot80}. Default: dot35";
      }
      leaf f2-intraslot-freq-hop {
        type boolean;
        default false;
        description "Enable intra-slot frequency hopping for PUCCH F2";
      }
      leaf f3-max-nof-rbs {
        type uint32;
        default 1;
        description "Max number of RBs for PUCCH F3 resources (legal values: {1, 2, 3, 4, 5, 6, 8, 9, 10, 12, 15, 16})";
      }
      leaf f3-max-payload {
        type uint32 {
          range "4..40";
        }
        description "Min required payload capacity in bits for PUCCH F3 resources";
      }
      leaf f3-max-code-rate {
        type enumeration {
          enum "dot08";
          enum "dot15";
          enum "dot25";
          enum "dot35";
          enum "dot45";
          enum "dot60";
          enum "dot80";
        }
        default "dot35";
        description "PUCCH F3 max code rate {dot08, dot15, dot25, dot35, dot45, dot60, dot80}. Default: dot35";
      }
      leaf f3-intraslot-freq-hop {
        type boolean;
        default false;
        description "Enable intra-slot frequency hopping for PUCCH F3";
      }
      leaf f3-additional-dmrs {
        type boolean;
        default false;
        description "Enable additional DM-RS for PUCCH F3";
      }
      leaf f3-pi2-bpsk {
        type boolean;
        default false;
        description "Enable pi/2-BPSK modulation for PUCCH F3";
      }
      leaf f4-max-code-rate {
        type enumeration {
          enum "dot08";
          enum "dot15";
          enum "dot25";
          enum "dot35";
          enum "dot45";
          enum "dot60";
          enum "dot80";
        }
        default "dot35";
        description "PUCCH F4 max code rate {dot08, dot15, dot25, dot35, dot45, dot60, dot80}. Default: dot35";
      }
      leaf f4-intraslot-freq-hop {
        type boolean;
        default false;
        description "Enable intra-slot frequency hopping for PUCCH F4";
      }
      leaf f4-additional-dmrs {
        type boolean;
        default false;
        description "Enable additional DM-RS for PUCCH F4";
      }
      leaf f4-pi2-bpsk {
        type boolean;
        default false;
        description "Enable pi/2-BPSK modulation for PUCCH F4";
      }
      leaf f4-occ-length {
        type uint32;
        default 2;
        description "OCC length for PUCCH F4 (legal values: {2, 4})";
      }
      leaf f4-enable-occ {
        type boolean;
        default false;
        description "Enable OCC multiplexing for PUCCH F4";
      }
      leaf min-k1 {
        type uint32 {
          range "1..4";
        }
        default 4;
        description "Minimum value of K1 (difference in slots between PDSCH and HARQ-ACK). Lower k1 values will reduce latency, but place a stricter requirement on the UE decode latency.";
      }
      leaf max-consecutive-kos {
        type uint32;
        default 100;
        description "Maximum number of consecutive undecoded PUCCH F2 for CSI before an Radio Link Failure is reported";
      }
      leaf enable-cl-loop-pw-control {
        type boolean;
        default false;
        description "Enable closed-loop power control for PUCCH";
      }
      leaf target-sinr-f0 {
        type decimal64 {
          fraction-digits 6;
          range "-10..20";
        }
        default 10;
        description "Target PUCCH F0 SINR in dB";
      }
      leaf target-sinr-f2 {
        type decimal64 {
          fraction-digits 6;
          range "-10..20";
        }
        default 6;
        description "Target PUCCH F2 SINR in dB";
      }
      leaf target-sinr-f3 {
        type decimal64 {
          fraction-digits 6;
          range "-15..10";
        }
        default 1;
        description "Target PUCCH F3 SINR in dB";
      }
    }
    container srs {
      description "SRS parameters";
      leaf type-enabled {
        type enumeration {
          enum "disabled";
          enum "periodic";
          enum "aperiodic";
        }
        default "disabled";
        description "Enable/disable SRS and set resource type";
      }
      leaf period-ms {
        type decimal64 {
          fraction-digits 6;
        }
        default 20;
        description "SRS period in ms. For aperiodic SRS, it indicates a tentative timing, and should not be interpreted as a precise period. The SRS period needs to be compatible with the subcarrier spacing (legal values: {1, 2, 2.5, 4, 5, 8, 10, 16, 20, 32, 40, 64, 80, 160, 320, 640, 1280, 2560})";
      }
      leaf max-nof-sym-per-slot {
        type uint32 {
          range "1..6";
        }
        default 2;
        description "Number of symbols for UL slot that are reserved for the SRS cell resources";
      }
      leaf nof-sym-per-resource {
        type uint32;
        default 1;
        description "Number of symbols per SRS resource (legal values: {1, 2, 4})";
      }
      leaf c-srs {
        type uint32 {
          range "0..63";
        }
        description "C_SRS parameter for SRS. If not set, it's computed automatically from the cell parameters";
      }
      leaf freq-domain-shift {
        type uint32 {
          range "0..268";
        }
        default 0;
        description "SRS frequency domain shift. Only applies if c_srs is set";
      }
      leaf tx-comb {
        type uint32;
        default 4;
        description "SRS TX comb size (legal values: {2, 4})";
      }
      leaf cyclic-shift-reuse {
        type uint32;
        default 1;
        description "SRS cyclic shift reuse factor. It needs to be compatible with the TX comb and number of UL antenna ports (legal values: {1, 2, 3, 4, 6})";
      }
      leaf sequence-id-reuse {
        type uint32;
        default 1;
        description "Enable the reuse of SRS sequence id with the set reuse factor (legal values: {1, 2, 3, 5, 6, 10, 15, 30})";
      }
      leaf p0 {
        type int32;
        default -84;
        description "P0 value for SRS. Value in dBm. Valid values must be multiple of 2 and within the [-202, 24] interval. Default: -84 (must be a multiple of 2 within [-202, 24])";
      }
    }
    container prach {
      description "PRACH parameters";
      leaf prach-config-index {
        type uint32 {
          range "0..255";
        }
        description "PRACH configuration index. If not set, the value is derived, so that the PRACH fits in an UL slot";
      }
      leaf prach-root-sequence-index {
        type uint32 {
          range "0..837";
        }
        default 1;
        description "PRACH root sequence index. NOTE: values: [0, 837] for PRACH format 0, 1, 2, 3. [0, 137] for other formats";
      }
      leaf zero-correlation-zone {
        type uint32 {
          range "0..15";
        }
        default 0;
        description "Zero correlation zone index";
      }
      leaf fixed-msg3-mcs {
        type uint32 {
          range "0..28";
        }
        default 0;
        description "Fixed message 3 MCS";
      }
      leaf max-msg3-harq-retx {
        type uint32 {
          range "0..4";
        }
        default 4;
        description "Maximum number of message 3 HARQ retransmissions";
      }
      leaf total-nof-ra-preambles {
        type uint32 {
          range "1..64";
        }
        default 64;
        description "Number of different contention-based PRACH preambles per occasion. If less than 64 preambles are used, the remaining preambles can be used for contention-free PRACHs";
      }
      leaf cfra-enabled {
        type boolean;
        default false;
        description "Whether to enable Contention-free Random Access (CFRA). If enabled, the total_nof_ra_preambles must be lower than 64";
      }
      leaf prach-frequency-start {
        type uint32 {
          range "0..274";
        }
        description "PRACH message frequency offset in PRBs. NOTE: When setting this parameter, it's up to user the ensure the PRACH opportunities do not overlap with the PUCCH resources";
      }
      leaf preamble-rx-target-pw {
        type int32;
        default -100;
        description "Target power level at the network receiver side, in dBm (must be a multiple of 2 within [-202, -60])";
      }
      leaf preamble-trans-max {
        type uint8;
        default 7;
        description "Max number of RA preamble transmissions performed before declaring a failure (legal values: {3, 4, 5, 6, 7, 8, 10, 20, 50, 100, 200})";
      }
      leaf power-ramping-step-db {
        type uint8;
        default 4;
        description "Power ramping steps for PRACH (legal values: {0, 2, 4, 6})";
      }
      leaf-list ports {
        type uint8;
        description "List of antenna ports";
      }
      leaf nof-ssb-per-ro {
        type uint8;
        default 3;
        description "Number of SSBs per RACH occasion (legal values: {1})";
      }
      leaf nof-cb-preambles-per-ssb {
        type uint8 {
          range "1..64";
        }
        default 64;
        description "Number of Contention Based preambles per SSB";
      }
      leaf ra-resp-window {
        type uint32;
        description "RA-Response window length in number of slots. (legal values: {1, 2, 4, 8, 10, 20, 40, 80})";
      }
      leaf nof-prach-guardbands-rbs {
        type uint32 {
          range "1..10";
        }
        default 3;
        description "Number of RBs that are used as guardband on each side of the PRACH RBs interval for short PRACH formats.";
      }
      list slice-based-ra-prioritization {
        // WARNING: no key designated; YANG list requires `key`. Use .key("...") at declaration.
        description "List of configurations for slice-based RA prioritization";
        leaf power-ramp-step-high-priority {
          type uint32;
          default 0;
          description "Power ramping step applied for prioritized random access procedure [dB]. (legal values: {0, 2, 4, 6})";
        }
        leaf scaling-factor-bi {
          type decimal64 {
            fraction-digits 6;
          }
          description "Scaling factor for backoff indicator (BI) for the prioritized RA procedure. (legal values: {0.0, 0.25, 0.5, 0.75})";
        }
        leaf-list nsag-ids {
          type uint8;
          description "NSAGs associated with this prioritized RA configuration.";
        }
      }
      container two-step {
        description "Two-step RACH (MsgA/MsgB) configuration";
        leaf cb-preambles-per-ssb-per-shared-ro {
          type uint8 {
            range "1..60";
          }
          default 4;
          description "Number of CB preambles per SSB per shared RACH occasion for 2-step RA";
        }
        leaf msgA-rsrp-thres-dbm {
          type int32 {
            range "-156..-29";
          }
          default -100;
          description "RSRP threshold in dBm above which the UE selects 2-step RA over 4-step RA";
        }
        leaf msgB-response-window-slots {
          type uint32;
          default 40;
          description "MsgB response window length in slots (legal values: {1, 2, 4, 8, 10, 20, 40, 80, 160, 320})";
        }
        leaf td-offset {
          type uint8 {
            range "1..32";
          }
          default 1;
          description "Time-domain offset in slots from the PRACH slot to the MsgA PUSCH slot";
        }
        leaf pusch-td-res-index {
          type uint8;
          default 0;
          description "Index into the PUSCH-TimeDomainAllocationResource table for MsgA PUSCH scheduling";
        }
        leaf mcs {
          type uint8 {
            range "0..28";
          }
          default 0;
          description "MCS index for MsgA PUSCH transmission";
        }
        leaf nof-prbs-per-msgA-po {
          type uint8 {
            range "1..32";
          }
          default 3;
          description "Number of PRBs per MsgA PUSCH occasion";
        }
        leaf prb-start {
          type uint32;
          default 0;
          description "Frequency offset in PRBs of the lowest MsgA PUSCH occasion from PRB 0";
        }
        leaf po-fdm {
          type uint8;
          default 1;
          description "Number of MsgA PUSCH occasions FDMed in one time instance (legal values: {1, 2, 4, 8})";
        }
      }
    }
    container tdd-ul-dl-cfg {
      description "TDD UL DL configuration parameters";
      leaf dl-ul-tx-period {
        type uint32 {
          range "2..80";
        }
        default 10;
        description "TDD pattern periodicity in slots. The combination of this value and the chosen numerology must lead to a TDD periodicity of 0.5, 0.625, 1, 1.25, 2, 2.5, 3, 4, 5 or 10 milliseconds.";
      }
      leaf nof-dl-slots {
        type uint32 {
          range "0..80";
        }
        default 6;
        description "TDD pattern nof. consecutive full DL slots";
      }
      leaf nof-dl-symbols {
        type uint32 {
          range "0..13";
        }
        default 8;
        description "TDD pattern nof. DL symbols at the beginning of the slot following full DL slots";
      }
      leaf nof-ul-slots {
        type uint32 {
          range "0..80";
        }
        default 3;
        description "TDD pattern nof. consecutive full UL slots";
      }
      leaf nof-ul-symbols {
        type uint32 {
          range "0..13";
        }
        default 0;
        description "TDD pattern nof. UL symbols at the end of the slot preceding the first full UL slot";
      }
      container pattern2 {
        description "TDD UL DL pattern2 configuration parameters";
        leaf dl-ul-tx-period {
          type uint32 {
            range "2..80";
          }
          default 10;
          description "TDD pattern periodicity in slots. The combination of this value and the chosen numerology must lead to a TDD periodicity of 0.5, 0.625, 1, 1.25, 2, 2.5, 3, 4, 5 or 10 milliseconds.";
        }
        leaf nof-dl-slots {
          type uint32 {
            range "0..80";
          }
          default 6;
          description "TDD pattern nof. consecutive full DL slots";
        }
        leaf nof-dl-symbols {
          type uint32 {
            range "0..13";
          }
          default 8;
          description "TDD pattern nof. DL symbols at the beginning of the slot following full DL slots";
        }
        leaf nof-ul-slots {
          type uint32 {
            range "0..80";
          }
          default 3;
          description "TDD pattern nof. consecutive full UL slots";
        }
        leaf nof-ul-symbols {
          type uint32 {
            range "0..13";
          }
          default 0;
          description "TDD pattern nof. UL symbols at the end of the slot preceding the first full UL slot";
        }
      }
    }
    container paging {
      description "Paging parameters";
      leaf pg-search-space-id {
        type uint32;
        default 1;
        description "SearchSpace to use for Paging (legal values: {0, 1})";
      }
      leaf default-pg-cycle-in-rf {
        type uint32;
        default 128;
        description "Default Paging cycle in nof. Radio Frames (legal values: {32, 64, 128, 256})";
      }
      leaf nof-pf-per-paging-cycle {
        type enumeration {
          enum "oneT";
          enum "halfT";
          enum "quarterT";
          enum "oneEighthT";
          enum "oneSixteethT";
        }
        default "oneT";
        description "Number of paging frames per DRX cycle {oneT, halfT, quarterT, oneEighthT, oneSixteethT}. Default: oneT";
      }
      leaf pf-offset {
        type uint32;
        default 0;
        description "Paging frame offset";
      }
      leaf nof-po-per-pf {
        type uint32;
        default 1;
        description "Number of paging occasions per paging frame (legal values: {1, 2, 4})";
      }
      leaf edrx-enabled {
        type boolean;
        default false;
        description "Enable eDRX";
      }
    }
    container csi {
      description "CSI-Meas parameters";
      leaf csi-rs-enabled {
        type boolean;
        default true;
        description "Enable CSI-RS resources and CSI reporting";
      }
      leaf csi-rs-period {
        type uint32;
        default 20;
        description "CSI-RS period in milliseconds (legal values: {10, 20, 40, 80})";
      }
      leaf report-type {
        type enumeration {
          enum "periodic";
          enum "aperiodic";
        }
        default "periodic";
        description "Type of CSI reporting configuration to use";
      }
      leaf meas-csi-rs-slot-offset {
        type uint32;
        description "Slot offset of first CSI-RS resource used for measurement";
      }
      leaf tracking-csi-rs-slot-offset {
        type uint32;
        description "Slot offset of first CSI-RS resource used for tracking";
      }
      leaf zp-csi-rs-slot-offset {
        type uint32;
        description "Slot offset of the ZP CSI-RS resources";
      }
      leaf pwr-ctrl-offset {
        type int32 {
          range "-8..15";
        }
        default 0;
        description "powerControlOffset, Power offset of PDSCH RE to NZP CSI-RS RE in dB";
      }
    }
    container scheduler {
      description "Scheduler parameters";
      leaf nof-preselected-newtx-ues {
        type uint32 {
          range "1..8192";
        }
        default 1024;
        description "Number of UEs pre-selected for potential newTx allocations in a slot. The scheduling policy will only be applied to the pre-selected UEs.";
      }
      container policy {
        description "Scheduler policy configuration. By default, time-domain QoS-aware policy is used.";
        container qos-sched {
          description "Time-domain QoS-aware policy configuration";
          leaf combine-function {
            type enumeration {
              enum "gbr_prioritized";
              enum "geometric_mean";
            }
            default "gbr_prioritized";
            description "QoS-aware scheduler policy weight combining function";
          }
          leaf pf-fairness-coeff {
            type decimal64 {
              fraction-digits 6;
            }
            default 2;
            description "Fairness Coefficient to use in Proportional Fair (PF) weight";
          }
          leaf prio-enabled {
            type boolean;
            default true;
            description "Whether to take into account the QoS Flow priority in QoS-aware scheduling";
          }
          leaf pdb-enabled {
            type boolean;
            default true;
            description "Whether to take into account the QoS Flow Packet Delay Budget (PDB) in QoS-aware scheduling";
          }
          leaf gbr-enabled {
            type boolean;
            default true;
            description "Whether to take into account the QoS Flow Guaranteed Bit Rate (GBR) in QoS-aware scheduling";
          }
        }
        container rr-sched {
          description "Time-domain Round-robin policy configuration";
        }
      }
    }
    container ta {
      description "Time Advance (TA) parameters";
      leaf ta-measurement-slot-period {
        type uint32;
        default 80;
        description "Measurements periodicity in number of slots over which the new Timing Advance Command is computed";
      }
      leaf ta-measurement-slot-prohibit-period {
        type uint32 {
          range "0..10000";
        }
        default 0;
        description "Delay in number of slots between issuing the TA_CMD and starting TA measurements.";
      }
      leaf ta-cmd-offset-threshold {
        type int32 {
          range "-1..31";
        }
        default 1;
        description "Timing Advance Command (T_A) offset threshold above which Timing Advance Command is triggered. If set to less than zero, issuing of TA Command is disabled";
      }
      leaf ta-target {
        type decimal64 {
          fraction-digits 6;
          range "-30..30";
        }
        default 1;
        description "Timing Advance target in units of TA";
      }
      leaf ta-update-measurement-ul-sinr-threshold {
        type decimal64 {
          fraction-digits 6;
        }
        default 0;
        description "UL SINR threshold (in dB) above which reported N_TA update measurement is considered valid";
      }
      leaf ta-outlier-detection-zscore-threshold {
        type decimal64 {
          fraction-digits 6;
          range "0..5";
        }
        default 1.75;
        description "Z-score threshold for outlier detection in N_TA measurements. Controls the sensitivity of the outlier detection algorithm. A lower value makes the filter more aggressive (rejects more measurements), while a higher value makes it more permissive. Typical values range from 1.5 to 3.0. Setting to 0.0 disables outlier detection.";
      }
    }
    container drx {
      description "DRX parameters";
      leaf on-duration-timer {
        type uint32;
        default 10;
        description "Minimum duration in milliseconds that the UE stays in active mode, when DRX is configured. (legal values: drx_helper::valid_on_duration_timer_values())";
      }
      leaf inactivity-timer {
        type uint32;
        default 0;
        description "Duration in milliseconds that the UE stays active after PDCCH reception, when DRX is configured. (legal values: drx_helper::valid_inactivity_timer_values())";
      }
      leaf retx-timer-dl {
        type uint32;
        default 0;
        description "Maximum duration in slots until a DL ReTX is received by the UE, when DRX is configured. (legal values: drx_helper::valid_retx_timer_values())";
      }
      leaf retx-timer-ul {
        type uint32;
        default 0;
        description "Maximum duration in slots until a grant for UL ReTX is received by the UE, when DRX is configured. (legal values: drx_helper::valid_retx_timer_values())";
      }
      leaf long-cycle {
        type uint32;
        default 0;
        description "Duration in milliseconds between UE DRX long cycles. The value 0 is used to disable DRX (legal values: drx_helper::valid_long_cycle_values() ∪ {0})";
      }
    }
    list slicing {
      // WARNING: no key designated; YANG list requires `key`. Use .key("...") at declaration.
      description "Network slicing configuration";
      leaf sst {
        type uint8 {
          range "0..255";
        }
        default 0;
        description "Slice Service Type";
      }
      leaf sd {
        type uint32 {
          range "0..16777215";
        }
        default 16777215;
        description "Service Differentiator";
      }
      container sched-cfg {
        description "Slice scheduling configuration";
        leaf min-prb-policy-ratio {
          type uint32 {
            range "0..100";
          }
          default 0;
          description "Minimum percentage of PRBs to be allocated to the slice";
        }
        leaf max-prb-policy-ratio {
          type uint32 {
            range "1..100";
          }
          default 100;
          description "Maximum percentage of PRBs to be allocated to the slice";
        }
        leaf ded-prb-policy-ratio {
          type uint32 {
            range "1..100";
          }
          default 0;
          description "Dedicated percentage of PRBs to be allocated to the slice";
        }
        leaf priority {
          type uint32 {
            range "0..254";
          }
          default 0;
          description "Slice priority";
        }
        container policy {
          description "Scheduler policy configuration for the slice. If not specified, the policy configured for the cell is used";
          container qos-sched {
            description "Time-domain QoS-aware policy configuration";
            leaf combine-function {
              type enumeration {
                enum "gbr_prioritized";
                enum "geometric_mean";
              }
              default "gbr_prioritized";
              description "QoS-aware scheduler policy weight combining function";
            }
            leaf pf-fairness-coeff {
              type decimal64 {
                fraction-digits 6;
              }
              default 2;
              description "Fairness Coefficient to use in Proportional Fair (PF) weight";
            }
            leaf prio-enabled {
              type boolean;
              default true;
              description "Whether to take into account the QoS Flow priority in QoS-aware scheduling";
            }
            leaf pdb-enabled {
              type boolean;
              default true;
              description "Whether to take into account the QoS Flow Packet Delay Budget (PDB) in QoS-aware scheduling";
            }
            leaf gbr-enabled {
              type boolean;
              default true;
              description "Whether to take into account the QoS Flow Guaranteed Bit Rate (GBR) in QoS-aware scheduling";
            }
          }
          container rr-sched {
            description "Time-domain Round-robin policy configuration";
          }
        }
      }
    }
    container ntn {
      description "NTN configuration";
      leaf cell-specific-koffset {
        type int64 {
          range "1..1023";
        }
        default 0;
        description "Cell-specific k-offset to be used for NTN [ms].";
      }
      leaf ntn-ul-sync-validity-dur {
        type uint32;
        description "An UL sync validity duration (legal values: {5, 10, 15, 20, 25, 30, 35, 40, 45, 50, 55, 60, 120, 180, 240, 900})";
      }
      container epoch-time {
        description "Epoch time for the NTN assistance information";
        leaf sfn {
          type uint32 {
            range "0..1023";
          }
          default 0;
          description "SFN Part";
        }
        leaf subframe-number {
          type uint32 {
            range "0..9";
          }
          default 0;
          description "Sub-frame number Part";
        }
      }
      container ta-info {
        description "TA Info for the NTN assistance information";
        leaf ta-common {
          type decimal64 {
            fraction-digits 6;
            range "0..270730";
          }
          default 0;
          description "TA common";
        }
        leaf ta-common-drift {
          type decimal64 {
            fraction-digits 6;
            range "-51.4606..51.4606";
          }
          default 0;
          description "Drift rate of the common TA";
        }
        leaf ta-common-drift-variant {
          type decimal64 {
            fraction-digits 6;
            range "0..0.57898";
          }
          default 0;
          description "Drift rate variation of the common TA";
        }
        leaf ta-common-offset {
          type decimal64 {
            fraction-digits 6;
            range "0..10000";
          }
          default 0;
          description "Constant offset added to TA common";
        }
      }
      container ephemeris-info-ecef {
        description "Ephermeris information of the satellite in ecef coordinates";
        leaf pos-x {
          type decimal64 {
            fraction-digits 6;
            range "-43620761.6..43620759.3";
          }
          default 0;
          description "X Position of the satellite [m]";
        }
        leaf pos-y {
          type decimal64 {
            fraction-digits 6;
            range "-43620761.6..43620759.3";
          }
          default 0;
          description "Y Position of the satellite [m]";
        }
        leaf pos-z {
          type decimal64 {
            fraction-digits 6;
            range "-43620761.6..43620759.3";
          }
          default 0;
          description "Z Position of the satellite [m]";
        }
        leaf vel-x {
          type decimal64 {
            fraction-digits 6;
            range "-7864.32..7864.26";
          }
          default 0;
          description "X Velocity of the satellite [m/s]";
        }
        leaf vel-y {
          type decimal64 {
            fraction-digits 6;
            range "-7864.32..7864.26";
          }
          default 0;
          description "Y Velocity of the satellite [m/s]";
        }
        leaf vel-z {
          type decimal64 {
            fraction-digits 6;
            range "-7864.32..7864.26";
          }
          default 0;
          description "Z Velocity of the satellite [m/s]";
        }
      }
      container ephemeris-orbital {
        description "Ephermeris information of the satellite in orbital coordinates";
        leaf semi-major-axis {
          type decimal64 {
            fraction-digits 6;
            range "6500000..42998632.07";
          }
          default 0;
          description "Semi-major axis of the satellite [m]";
        }
        leaf eccentricity {
          type decimal64 {
            fraction-digits 6;
            range "0..0.01500510825";
          }
          default 0;
          description "Eccentricity of the satellite [-]";
        }
        leaf periapsis {
          type decimal64 {
            fraction-digits 6;
            range "0..6.28407400155";
          }
          default 0;
          description "Periapsis of the satellite [rad]";
        }
        leaf longitude {
          type decimal64 {
            fraction-digits 6;
            range "0..6.28407400155";
          }
          default 0;
          description "Longitude of the satellites angle of ascending node [rad]";
        }
        leaf inclination {
          type decimal64 {
            fraction-digits 6;
            range "-1.57101850624..1.57101848283";
          }
          default 0;
          description "Inclination of the satellite [rad]";
        }
        leaf mean-anomaly {
          type decimal64 {
            fraction-digits 6;
            range "0..6.28407400155";
          }
          default 0;
          description "Mean anomaly of the satellite [rad]";
        }
      }
    }
    container rlm {
      description "Radio Link Monitoring parameters";
      leaf rlm-resource-type {
        type enumeration {
          enum "default_type";
          enum "ssb";
          enum "csi_rs";
          enum "ssb_and_csi_rs";
        }
        default "default_type";
        description "Radio Link Monitoring resource detection type {default_type, ssb, csi_rs, ssb_and_csi_rs}. Default: default_type";
      }
    }
  }
  container du {
    description "DU parameters";
    leaf warn-on-drop {
      type boolean;
      default false;
      description "Log a warning for dropped packets in F1-U, RLC and MAC due to full queues";
    }
  }
  list cells {
    // WARNING: no key designated; YANG list requires `key`. Use .key("...") at declaration.
    description "Sets the cell configuration on a per cell basis, overwriting the default configuration defined by cell_cfg";
    leaf pci {
      type uint16 {
        range "0..1007";
      }
      default 1;
      description "PCI";
    }
    leaf sector-id {
      type uint32 {
        range "0..16383";
      }
      description "Sector ID (4-14 bits). This value is concatenated with the gNB Id to form the NR Cell Identity (NCI). If not specified, a unique value for the DU is automatically derived";
    }
    leaf dl-arfcn {
      type string;
      default "536020";
      description "Downlink ARFCN (non-negative integer; valid range [0, 3279165])";
    }
    leaf band {
      type int32;
      default auto;
      description "NR band (set to \"auto\" to auto-derive)";
    }
    leaf common-scs {
      type string;
      default "15kHz";
      description "Cell common subcarrier spacing (accepts SCS strings (e.g. \"15kHz\", \"30kHz\"))";
    }
    leaf channel-bandwidth-MHz {
      type int32;
      default 20;
      description "Channel bandwidth in MHz (legal values: {5, 10, 15, 20, 25, 30, 40, 50, 60, 70, 80, 90, 100, 200, 400})";
    }
    leaf nof-antennas-ul {
      type uint32;
      default 1;
      description "Number of antennas in uplink";
    }
    leaf nof-antennas-dl {
      type uint32;
      default 1;
      description "Number of antennas in downlink";
    }
    leaf plmn {
      type string {
        pattern "[0-9]{5,6}";
      }
      default "00101";
      description "PLMN";
    }
    leaf-list additional-plmns {
      type string;
      description "List of PLMNs (each element must be a valid PLMN string)";
    }
    leaf tac {
      type uint32;
      default 7;
      description "TAC (values 0 and 0xfffffe are reserved; value must fit in 24 bits)";
    }
    leaf enabled {
      type boolean;
      default true;
      description "Automatically activate the cell on startup";
    }
    leaf cell-barred {
      type boolean;
      default false;
      description "MIB cellBarred: if true, UEs cannot camp on this cell";
    }
    leaf intra-freq-reselection {
      type boolean;
      default true;
      description "MIB intraFreqReselection: if true, intra-frequency cell reselection is allowed when cell is barred";
    }
    leaf q-rx-lev-min {
      type int32 {
        range "-70..-22";
      }
      default -70;
      description "q-RxLevMin, required minimum received RSRP level for cell selection/re-selection, in dBm";
    }
    leaf q-qual-min {
      type int32 {
        range "-43..-12";
      }
      default -20;
      description "q-QualMin, required minimum received RSRQ level for cell selection/re-selection, in dB";
    }
    leaf pcg-p-nr-fr1 {
      type int32 {
        range "-30..23";
      }
      description "p-nr-fr1, maximum total TX power to be used by the UE in this NR cell group across in FR1";
    }
    container mac-cell-group {
      description "MAC Cell Group parameters";
      container bsr-cfg {
        description "Buffer status report configuration parameters";
        leaf periodic-bsr-timer {
          type uint32;
          default 10;
          description "Periodic Buffer Status Report Timer value in nof. subframes. Value 0 equates to infinity (legal values: {1, 5, 10, 16, 20, 32, 40, 64, 80, 128, 160, 320, 640, 1280, 2560, 0})";
        }
        leaf retx-bsr-timer {
          type uint32;
          default 80;
          description "Retransmission Buffer Status Report Timer value in nof. subframes (legal values: {10, 20, 40, 80, 160, 320, 640, 1280, 2560, 5120, 10240})";
        }
        leaf lc-sr-delay-timer {
          type uint32;
          description "Logical Channel SR delay timer in nof. subframes (legal values: {20, 40, 64, 128, 512, 1024, 2560})";
        }
      }
      container phr-cfg {
        description "Power Headroom report configuration parameters";
        leaf phr-prohibit-timer {
          type uint32;
          default 10;
          description "PHR prohibit timer in nof. subframes (legal values: {0, 10, 20, 50, 100, 200, 500, 1000})";
        }
      }
      container sr-cfg {
        description "Scheduling Request configuration parameters";
        leaf sr-trans-max {
          type uint32;
          default 64;
          description "Maximum number of SR transmissions (legal values: {4, 8, 16, 32, 64})";
        }
        leaf sr-prohibit-timer {
          type uint32;
          description "Timer for SR transmission on PUCCH in ms (legal values: {1, 2, 4, 8, 16, 32, 64, 128})";
        }
      }
    }
    container ssb {
      description "SSB parameters";
      leaf ssb-period {
        type uint32;
        default 10;
        description "Period of SSB scheduling in milliseconds (legal values: {5, 10, 20})";
      }
      leaf ssb-block-power-dbm {
        type int32 {
          range "-60..50";
        }
        default -16;
        description "SS_PBCH_power_block in dBm";
      }
      leaf pss-to-sss-epre {
        type enumeration {
          enum "0";
          enum "3";
        }
        default "0";
        description "SSB PSS to SSS EPRE ratio in dB {0, 3} (legacy CLI11 accepted only the integer values 0 and 3; the builder API maps them to the string keys \"0\" and \"3\".)";
      }
    }
    container sib {
      description "SIB configuration parameters";
      leaf si-window-length {
        type uint32;
        default 160;
        description "The length of the SI scheduling window, in slots. It must be always shorter or equal to the period of the SI message. (legal values: {5, 10, 20, 40, 80, 160, 320, 640, 1280})";
      }
      list si-sched-info {
        // WARNING: no key designated; YANG list requires `key`. Use .key("...") at declaration.
        description "Configures the scheduling for each of the SI-messages broadcast by the gNB";
        leaf si-period {
          type uint32;
          default 32;
          description "SI message scheduling period in radio frames (legal values: {8, 16, 32, 64, 128, 256, 512})";
        }
        leaf-list sib-mapping {
          type uint8;
          description "Mapping of SIB types to SI-messages. SIB numbers should not be repeated (each element must be in {2, 3, 4, 5, 6, 7, 8, 19})";
        }
        leaf si-window-position {
          type uint32 {
            range "1..256";
          }
          description "SI window position of the associated SI-message";
        }
      }
      container sib2 {
        description "SIB2 parameters";
        leaf q-hyst {
          type uint32;
          default 3;
          description "Hysteresis value for ranking criteria. (legal values: {0, 1, 2, 3, 4, 5, 6, 8, 10, 12, 14, 16, 18, 20, 22, 24})";
        }
        leaf thresh-serving-low-p {
          type uint32 {
            range "0..31";
          }
          default 0;
          description "Rx level threshold used by the UE on the serving cell when reselecting towards a lower priority RAT/frequency.";
        }
        leaf cell-reselection-priority {
          type uint32 {
            range "0..7";
          }
          default 6;
          description "Integer part of the cell reselection priority for the frequency of this cell";
        }
        leaf q-rx-lev-min {
          type int32;
          default -140;
          description "Minimum required Rx level in the cell in dBm (must be an even value within [-140, -44])";
        }
        leaf s-intra-search-p {
          type uint32;
          default 62;
          description "Rx level threshold for intra frequency measurements in dB (must be an even value within [0, 62])";
        }
        leaf t-reselection-nr {
          type uint32 {
            range "0..7";
          }
          default 1;
          description "Cell reselection timer value in seconds";
        }
      }
      container sib3 {
        description "SIB3 parameters";
        list intra-freq-neigh-cell-list {
          // WARNING: no key designated; YANG list requires `key`. Use .key("...") at declaration.
          description "Intra frequency neighbor cell list";
          leaf pci {
            type uint16 {
              range "0..1007";
            }
            default 0;
            description "PCI";
          }
          leaf q-offset-cell {
            type int8;
            default 0;
            description "PCI (legal values: {-24, -22, -20, -18, -16, -14, -12, -10, -8, -6, -5, -4, -3, -2, -1, 0, 1, 2, 3, 4, 5, 6, 8, 10, 12, 14, 16, 18, 20, 22, 24})";
          }
        }
        list intra-freq-excluded-cell-list {
          // WARNING: no key designated; YANG list requires `key`. Use .key("...") at declaration.
          description "Intra frequency excluded cell list";
          leaf start {
            type uint16 {
              range "0..1007";
            }
            mandatory true;
            default 0;
            description "Range start";
          }
          leaf size {
            type uint32;
            mandatory true;
            default 1;
            description "Range size (legal values: {1, 4, 8, 12, 16, 24, 32, 48, 64, 84, 96, 128, 168, 252, 504, 1008})";
          }
        }
      }
      container sib4 {
        description "SIB4 parameters";
        list inter-freq-carrier-freq-list {
          // WARNING: no key designated; YANG list requires `key`. Use .key("...") at declaration.
          description "Inter frequency carrier frequency list";
          leaf arfcn {
            type uint32;
            default 0;
            description "ARFCN";
          }
          leaf ssb-scs {
            type string;
            default "15kHz";
            description "SSB subcarrier spacing (accepts SCS strings (e.g. \"15kHz\", \"30kHz\"))";
          }
          leaf derive-ssb-index-from-cell {
            type boolean;
            default false;
            description "Derive SSB index from cell";
          }
          leaf q-rx-lev-min {
            type int32;
            default -140;
            description "Minimum required Rx level in the cell in dBm (must be an even value within [-140, -44])";
          }
          leaf thresh-x-high-p {
            type uint32;
            default 0;
            description "Rx level threshold in dB used when reselecting to a higher priority RAT/frequency in dB (must be an even value within [0, 62])";
          }
          leaf thresh-x-low-p {
            type uint32;
            default 0;
            description "Rx level threshold in dB used when reselecting to a lower priority RAT/frequency in dB (must be an even value within [0, 62])";
          }
          leaf q-offset-freq {
            type int32;
            default 0;
            description "Frequency specific offset in dB for equal priority NR frequencies. (legal values: {-24, -22, -20, -18, -16, -14, -12, -10, -8, -6, -5, -4, -3, -2, -1, 0, 1, 2, 3, 4, 5, 6, 8, 10, 12, 14, 16, 18, 20, 22, 24})";
          }
        }
      }
      container sib5 {
        description "SIB5 parameters";
        leaf t-reselection-eutra {
          type uint32 {
            range "0..7";
          }
          default 0;
          description "Cell reselection timer value in seconds";
        }
        list carrier-freq-list-eutra {
          // WARNING: no key designated; YANG list requires `key`. Use .key("...") at declaration.
          description "EUTRA carrier frequency list";
          leaf earfcn {
            type uint32;
            default 0;
            description "EARFCN";
          }
          leaf allowed-meas-bandwidth {
            type uint32;
            default 0;
            description "Allowed measurement bandwidth (legal values: {6, 15, 25, 50, 75, 100})";
          }
          leaf presence-antenna-port1 {
            type boolean;
            default false;
            description "Whether all neighbor cells use Antenna Port 1";
          }
          leaf cell-reselection-priority {
            type uint32 {
              range "0..7";
            }
            description "Integer part of the cell reselection priority for the frequency of this cell";
          }
          leaf thresh-x-high {
            type uint32;
            default 0;
            description "Rx level threshold in dB used when reselecting to a higher priority RAT/frequency in dB (must be an even value within [0, 62])";
          }
          leaf thresh-x-low {
            type uint32;
            default 0;
            description "Rx level threshold in dB used when reselecting to a lower priority RAT/frequency in dB (must be an even value within [0, 62])";
          }
          leaf q-rx-lev-min {
            type int32;
            default -140;
            description "Minimum required Rx level in the cell in dBm (must be an even value within [-140, -44])";
          }
          leaf q-qual-min {
            type int32 {
              range "-34..-3";
            }
            default -34;
            description "Minimum required quality level in the cell in dB";
          }
          leaf p-max-eutra {
            type int32 {
              range "-30..33";
            }
            default 33;
            description "Maximum allowed transmission power in dBm on the (uplink) carrier frequency.";
          }
        }
      }
      container sib16 {
        description "SIB16 parameters";
        list freq-prio-list-slicing {
          // WARNING: no key designated; YANG list requires `key`. Use .key("...") at declaration.
          description "Frequency priority slicing list entries";
          leaf dl-implicit-carrier-freq {
            type uint32 {
              range "0..8";
            }
            default 0;
            description "DL implicit carrier frequency index for this slicing entry";
          }
          list slice-info-list {
            // WARNING: no key designated; YANG list requires `key`. Use .key("...") at declaration.
            description "Slice info list entries";
            leaf nsag-id {
              type uint32 {
                range "0..255";
              }
              default 0;
              description "NSAG ID";
            }
            leaf allowed {
              type boolean;
              default true;
              description "Whether the list of cells in this slice info is allowed (true) or excluded (false)";
            }
            leaf reselection-priority {
              type decimal64 {
                fraction-digits 6;
              }
              default 0;
              description "Priority associated with this cell reselection slice (must be a multiple of 0.2 within [0.0, 7.8])";
            }
            list cells-allowed {
              // WARNING: no key designated; YANG list requires `key`. Use .key("...") at declaration.
              description "Slice cell list entries";
              leaf start {
                type uint16 {
                  range "0..1007";
                }
                mandatory true;
                default 0;
                description "Range start";
              }
              leaf size {
                type uint32;
                mandatory true;
                default 1;
                description "Range size (legal values: {1, 4, 8, 12, 16, 24, 32, 48, 64, 84, 96, 128, 168, 252, 504, 1008})";
              }
            }
          }
        }
      }
      container etws {
        description "ETWS configuration parameters";
        leaf message-id {
          type uint32 {
            range "0..65535";
          }
          default 4356;
          description "ETWS message ID.";
        }
        leaf serial-num {
          type uint32 {
            range "0..65535";
          }
          default 12288;
          description "ETWS message serial number.";
        }
        leaf warning-type {
          type uint32 {
            range "0..65535";
          }
          default 2432;
          description "ETWS warning type.";
        }
        leaf data-coding-scheme {
          type uint32 {
            range "0..255";
          }
          default 0;
          description "ETWS message CBS coding scheme.";
        }
        leaf warning-message {
          type string;
          description "ETWS warning message. Max. Length and character support depends on the chosen coding scheme.";
        }
      }
      container cmas {
        description "CMAS configuration parameters";
        leaf message-id {
          type uint32 {
            range "0..65535";
          }
          default 4370;
          description "CMAS message ID.";
        }
        leaf serial-num {
          type uint32 {
            range "0..65535";
          }
          default 12291;
          description "CMAS message serial number.";
        }
        leaf data-coding-scheme {
          type uint32 {
            range "0..255";
          }
          default 0;
          description "CMAS message CBS coding scheme.";
        }
        leaf warning-message {
          type string;
          default "";
          description "CMAS warning message. Max. Length and character support depends on the chosen coding scheme.";
        }
      }
      leaf t300 {
        type uint32;
        default 1000;
        description "RRC Connection Establishment timer in ms. The timer starts upon transmission of RRCSetupRequest. (legal values: {100, 200, 300, 400, 600, 1000, 1500, 2000})";
      }
      leaf t301 {
        type uint32;
        default 1000;
        description "RRC Connection Re-establishment timer in ms. The timer starts upon transmission of RRCReestablishmentRequest. (legal values: {100, 200, 300, 400, 600, 1000, 1500, 2000})";
      }
      leaf t310 {
        type uint32;
        default 1000;
        description "Out-of-sync timer in ms. The timer starts upon detecting physical layer problems for the SpCell i.e. upon receiving N310 consecutive out-of-sync indications from lower layers. (legal values: {0, 50, 100, 200, 500, 1000, 2000})";
      }
      leaf n310 {
        type uint32;
        default 1;
        description "Out-of-sync counter. The counter is increased upon reception of \"out-of-sync\" from lower layer while the timer T310 is stopped. Starts the timer T310, when configured value is reached. (legal values: {1, 2, 3, 4, 6, 8, 10, 20})";
      }
      leaf t311 {
        type uint32;
        default 3000;
        description "RRC Connection Re-establishment procedure timer in ms. The timer starts upon initiating the RRC connection re-establishment procedure. (legal values: {1000, 3000, 5000, 10000, 15000, 20000, 30000})";
      }
      leaf n311 {
        type uint32;
        default 1;
        description "In-sync counter. The counter is increased upon reception of the \"in-sync\" from lower layer while the timer T310 is running. Stops the timer T310, when configured value is reached. (legal values: {1, 2, 3, 4, 5, 6, 8, 10})";
      }
      leaf t319 {
        type uint32;
        default 1000;
        description "RRC Connection Resume timer in ms. The timer starts upon transmission of RRCResumeRequest or RRCResumeRequest1. (legal values: {100, 200, 300, 400, 600, 1000, 1500, 2000})";
      }
    }
    container ul-common {
      description "UL common parameters";
      leaf p-max {
        type int32 {
          range "-30..23";
        }
        description "Maximum transmit power allowed in this serving cell";
      }
      leaf max-pucchs-per-slot {
        type uint32 {
          range "1..128";
        }
        default 31;
        description "Maximum number of PUCCH grants that can be allocated per slot";
      }
      leaf max-ul-grants-per-slot {
        type uint32 {
          range "1..144";
        }
        default 32;
        description "Maximum number of UL grants that can be allocated per slot";
      }
      leaf min-pucch-pusch-prb-distance {
        type uint32 {
          range "0..137";
        }
        default 1;
        description "Minimum PRB distance between PUCCH and UE-dedicated PUSCH grants";
      }
    }
    container pdcch {
      description "PDCCH parameters";
      container common {
        description "PDCCH Common configuration parameters";
        leaf coreset0-index {
          type uint32 {
            range "0..15";
          }
          description "CORESET#0 index";
        }
        leaf ss1-n-candidates {
          type string;
          default "[0,0,1,0,0]";
          description "Number of PDCCH candidates per aggregation level for SearchSpace#1. Default: {0, 0, 1, 0, 0} (5-element list of uint8_t (e.g. \"[0,0,1,0,0]\"). Each element must be in {0,1,2,3,4,5,6,8}.) (legacy CLI11 accepted a YAML list of integers; the builder API stores the value as a single string.)";
        }
        leaf ss0-index {
          type uint32 {
            range "0..15";
          }
          default 0;
          description "SearchSpace#0 index";
        }
        leaf max-coreset0-duration {
          type uint8 {
            range "1..2";
          }
          description "Maximum CORESET#0 duration in OFDM symbols to consider when deriving CORESET#0 index";
        }
      }
      container dedicated {
        description "PDCCH Dedicated configuration parameters";
        leaf coreset1-rb-start {
          type uint32 {
            range "0..275";
          }
          description "Starting Common Resource Block (CRB) number for CORESET 1 relative to CRB 0. Default: CRB0";
        }
        leaf coreset1-l-crb {
          type uint32 {
            range "0..275";
          }
          description "Length of CORESET 1 in number of CRBs. Default: Across entire BW of cell";
        }
        leaf coreset1-duration {
          type uint32 {
            range "1..2";
          }
          description "Duration of CORESET 1 in number of OFDM symbols. Default: Max(2, Nof. CORESET#0 symbols)";
        }
        leaf ss2-n-candidates {
          type string;
          default "[0,0,0,0,0]";
          description "Number of PDCCH candidates per aggregation level for SearchSpace#2. Default: {0, 0, 0, 0, 0} i.e. auto-compute nof. candidates (5-element list of uint8_t (e.g. \"[0,0,0,0,0]\"). Each element must be in {0,1,2,3,4,5,6,8}.) (legacy CLI11 accepted a YAML list of integers; the builder API stores the value as a single string.)";
        }
        leaf dci-format-0-1-and-1-1 {
          type boolean;
          default true;
          description "DCI format to use in UE dedicated SearchSpace#2";
        }
        leaf ss2-type {
          type enumeration {
            enum "common";
            enum "ue_dedicated";
          }
          default "ue_dedicated";
          description "SearchSpace type for UE dedicated SearchSpace#2";
        }
        leaf al-cqi-offset {
          type decimal64 {
            fraction-digits 6;
            range "-15..15";
          }
          default 0;
          description "Offset to apply to the CQI value used in the PDCCH aggregation level calculation.";
        }
      }
    }
    container pdsch {
      description "PDSCH parameters";
      leaf min-ue-mcs {
        type uint32 {
          range "0..28";
        }
        default 0;
        description "Minimum UE MCS";
      }
      leaf max-ue-mcs {
        type uint32 {
          range "0..28";
        }
        default 28;
        description "Maximum UE MCS";
      }
      leaf fixed-rar-mcs {
        type uint32 {
          range "0..28";
        }
        default 0;
        description "Fixed RAR MCS";
      }
      leaf fixed-sib1-mcs {
        type uint32 {
          range "0..28";
        }
        default 5;
        description "Fixed SIB1 MCS";
      }
      leaf harq-feedback-disabled {
        type string;
        default "false";
        description "Disable DL HARQ Feedback (only for NTN cells).
If set to true, applies the mask 0x0fffffff and disables HARQ feedback for all except the first four HARQs.
If set to a string, it must be a 32-bit bitmap (0x… or 0b…) of the HARQ processes to disable.
The bit set to 1 indicates HARQ processes with disabled DL HARQ feedback and the bit set to 0,
identify HARQ processes with enabled DL HARQ feedback.The leftmost bit corresponds to HARQ process ID 0; bits for unconfigured HARQ process IDs are ignored.
 (accepts \"true\", \"false\" or a 32-bit bitmap (\"0x...\" / \"0b...\").)";
      }
      leaf nof-harqs {
        type uint32;
        default 16;
        description "Number of DL HARQ processes. The value 32 is applied only for NTN cells when supported by the UE; otherwise, it defaults to 16. (legal values: {2, 4, 6, 8, 10, 12, 16, 32})";
      }
      leaf max-nof-harq-retxs {
        type uint32 {
          range "0..64";
        }
        default 4;
        description "Maximum number of times a DL HARQ can be retransmitted, before it gets discarded.";
      }
      leaf harq-retx-timeout {
        type uint32 {
          range "10..500";
        }
        default 100;
        description "Maximum time, in milliseconds, between a HARQ NACK and the scheduler allocating the respective HARQ for retransmission. If this timeout is exceeded, the HARQ process is discarded.";
      }
      leaf max-consecutive-kos {
        type uint32;
        default 100;
        description "Maximum number of HARQ-ACK consecutive KOs before an Radio Link Failure is reported";
      }
      leaf-list rv-sequence {
        type uint32;
        description "RV sequence for PUSCH. (e.g. [0 2 3 1] (each element must be in {0, 1, 2, 3})";
      }
      leaf mcs-table {
        type enumeration {
          enum "qam64";
          enum "qam256";
          enum "qam64lowse";
        }
        default "qam256";
        description "MCS table to use PDSCH";
      }
      leaf min-rb-size {
        type uint32 {
          range "1..275";
        }
        default 1;
        description "Minimum RB size for UE PDSCH resource allocation";
      }
      leaf max-rb-size {
        type uint32 {
          range "1..275";
        }
        default 275;
        description "Maximum RB size for UE PDSCH resource allocation";
      }
      leaf start-rb {
        type uint32 {
          range "0..275";
        }
        default 0;
        description "Start RB for resource allocation of UE PDSCHs";
      }
      leaf end-rb {
        type uint32 {
          range "0..275";
        }
        default 275;
        description "End RB for resource allocation of UE PDSCHs";
      }
      leaf max-pdschs-per-slot {
        type uint32 {
          range "1..35";
        }
        default 35;
        description "Maximum number of PDSCH grants per slot, including SIB, RAR, Paging and UE data grants.";
      }
      leaf max-alloc-attempts {
        type uint32 {
          range "1..35";
        }
        default 35;
        description "Maximum number of DL or UL PDCCH grant allocation attempts per slot before scheduler skips the slot";
      }
      leaf olla-cqi-inc-step {
        type decimal64 {
          fraction-digits 6;
          range "0..1";
        }
        default 0.001;
        description "Outer-loop link adaptation (OLLA) increment value. The value 0 means that OLLA is disabled";
      }
      leaf olla-target-bler {
        type decimal64 {
          fraction-digits 6;
          range "0..0.5";
        }
        default 0.01;
        description "Target DL BLER set in Outer-loop link adaptation (OLLA) algorithm";
      }
      leaf olla-max-cqi-offset {
        type decimal64 {
          fraction-digits 6;
          range "0..max";
        }
        default 4;
        description "Maximum offset that the Outer-loop link adaptation (OLLA) can apply to CQI";
      }
      leaf dc-offset {
        type string;
        default "center";
        description "Direct Current (DC) Offset in number of subcarriers, using the common SCS as reference for carrier spacing, and the center of the gNB DL carrier as DC offset value 0. The user can additionally set \"outside\" to define that the DC offset falls outside the DL carrier or \"undetermined\" in the case the DC offset is unknown. (accepts an integer in [min,max] or one of {\"outside\",\"undetermined\",\"center\"}.)";
      }
      leaf harq-la-cqi-drop-threshold {
        type uint8 {
          range "0..15";
        }
        default 3;
        description "Link Adaptation (LA) threshold for drop in CQI of the first HARQ transmission above which HARQ retransmissions are cancelled. Set this value to 0 to disable this feature";
      }
      leaf harq-la-ri-drop-threshold {
        type uint8 {
          range "0..4";
        }
        default 1;
        description "Link Adaptation (LA) threshold for drop in nof. layers of the first HARQ transmission above which HARQ retransmission is cancelled. Set this value to 0 to disable this feature";
      }
      leaf dmrs-additional-position {
        type uint32 {
          range "0..3";
        }
        default 2;
        description "PDSCH DMRS additional position";
      }
      leaf interleaving-bundle-size {
        type uint8;
        default 0;
        description "PDSCH interleaving bundle size. Valid values: [0, 2, 4] (legal values: {0, 2, 4})";
      }
      leaf max-rank {
        type uint32 {
          range "0..max";
        }
        description "Maximum number of PDSCH transmission layers. The actual maximum is limited by the number of DL antennas.";
      }
      leaf enable-csi-rs-pdsch-multiplexing {
        type boolean;
        default true;
        description "Enable multiplexing of CSI-RS and PDSCH";
      }
    }
    container pusch {
      description "PUSCH parameters";
      leaf min-ue-mcs {
        type uint32 {
          range "0..28";
        }
        default 0;
        description "Minimum UE MCS";
      }
      leaf max-ue-mcs {
        type uint32 {
          range "0..28";
        }
        default 28;
        description "Maximum UE MCS";
      }
      leaf harq-mode-b {
        type string;
        default "false";
        description "Set HARQ Mode B (only for NTN cells).
If set to true, applies the mask 0x0fffffff to set HARQ Mode B for all except the first four HARQ processes.
If set to a string, it must be a 32-bit bitmap (0x… or 0b…) indicating which HARQ processes use Mode B.
A bit set to 1 indicates HARQ Mode B; a bit set to 0 indicates HARQ Mode A.
The leftmost bit corresponds to HARQ process ID 0; bits for unconfigured HARQ process IDs are ignored.
 (accepts \"true\", \"false\" or a 32-bit bitmap (\"0x...\" / \"0b...\").)";
      }
      leaf nof-harqs {
        type uint32;
        default 16;
        description "Number of UL HARQ processes. The value 32 is applied only for NTN cells when supported by the UE; otherwise, it defaults to 16. (legal values: {16, 32})";
      }
      leaf max-nof-harq-retxs {
        type uint32 {
          range "0..64";
        }
        default 4;
        description "Maximum number of times a UL HARQ can be retransmitted, before it gets discarded.";
      }
      leaf harq-retx-timeout {
        type uint32 {
          range "10..500";
        }
        default 100;
        description "Maximum time, in milliseconds, between a CRC=KO and the scheduler allocating the respective HARQ for retransmission. If this timeout is exceeded, the HARQ process is discarded.";
      }
      leaf max-consecutive-kos {
        type uint32;
        default 100;
        description "Maximum number of CRC consecutive KOs before an Radio Link Failure is reported";
      }
      leaf-list rv-sequence {
        type uint32;
        description "RV sequence for PUSCH. (e.g. [0 2 3 1] (each element must be in {0, 1, 2, 3})";
      }
      leaf mcs-table {
        type enumeration {
          enum "qam64";
          enum "qam256";
          enum "qam64lowse";
        }
        default "qam256";
        description "MCS table to use PUSCH";
      }
      leaf max-rank {
        type uint32 {
          range "1..4";
        }
        default 4;
        description "Maximum number of PUSCH transmission layers. The actual maximum is limited by the number of receive ports and UE capabilities.";
      }
      leaf msg3-delta-preamble {
        type int32 {
          range "-1..6";
        }
        default 6;
        description "msg3-DeltaPreamble, Power offset between msg3 and RACH preamble transmission";
      }
      leaf p0-nominal-with-grant {
        type int32;
        default -76;
        description "P0 value for PUSCH with grant (except msg3). Value in dBm. Valid values must be multiple of 2 and within the [-202, 24] interval.  Default: -76 (must be a multiple of 2 within [-202, 24])";
      }
      leaf msg3-delta-power {
        type int32;
        default 8;
        description "Target power level at the network receiver side, in dBm. Valid values must be multiple of 2 and within the [-6, 8] interval. Default: 8 (must be a multiple of 2 within [-6, 8])";
      }
      leaf max-puschs-per-slot {
        type uint32 {
          range "1..16";
        }
        default 16;
        description "Maximum number of PUSCH grants per slot";
      }
      leaf beta-offset-ack-idx-1 {
        type uint32 {
          range "0..31";
        }
        default 11;
        description "betaOffsetACK-Index1 part of UCI-OnPUSCH";
      }
      leaf beta-offset-ack-idx-2 {
        type uint32 {
          range "0..31";
        }
        default 6;
        description "betaOffsetACK-Index2 part of UCI-OnPUSCH";
      }
      leaf beta-offset-ack-idx-3 {
        type uint32 {
          range "0..31";
        }
        default 4;
        description "betaOffsetACK-Index3 part of UCI-OnPUSCH";
      }
      leaf beta-offset-csi-p1-idx-1 {
        type uint32 {
          range "0..31";
        }
        default 13;
        description "betaOffsetCSI-Part1-Index1 part of UCI-OnPUSCH";
      }
      leaf beta-offset-csi-p1-idx-2 {
        type uint32 {
          range "0..31";
        }
        default 10;
        description "betaOffsetCSI-Part1-Index2 part of UCI-OnPUSCH";
      }
      leaf beta-offset-csi-p2-idx-1 {
        type uint32 {
          range "0..31";
        }
        default 13;
        description "betaOffsetCSI-Part2-Index1 part of UCI-OnPUSCH";
      }
      leaf beta-offset-csi-p2-idx-2 {
        type uint32 {
          range "0..31";
        }
        default 10;
        description "betaOffsetCSI-Part2-Index2 part of UCI-OnPUSCH";
      }
      leaf min-k2 {
        type uint32 {
          range "1..4";
        }
        default 4;
        description "Minimum value of K2 (difference in slots between PDCCH and PUSCH).";
      }
      leaf dc-offset {
        type string;
        default "center";
        description "Direct Current (DC) Offset in number of subcarriers, using the common SCS as reference for carrier spacing, and the center of the gNB UL carrier as DC offset value 0. The user can additionally set \"outside\" to define that the DC offset falls outside the UL carrier or \"undetermined\" in the case the DC offset is unknown. (accepts an integer in [min,max] or one of {\"outside\",\"undetermined\",\"center\"}.)";
      }
      leaf olla-snr-inc-step {
        type decimal64 {
          fraction-digits 6;
          range "0..1";
        }
        default 0.001;
        description "Outer-loop link adaptation (OLLA) increment value. The value 0 means that OLLA is disabled";
      }
      leaf olla-target-bler {
        type decimal64 {
          fraction-digits 6;
          range "0..0.5";
        }
        default 0.01;
        description "Target UL BLER set in Outer-loop link adaptation (OLLA) algorithm";
      }
      leaf olla-max-snr-offset {
        type decimal64 {
          fraction-digits 6;
          range "0..max";
        }
        default 5;
        description "Maximum offset that the Outer-loop link adaptation (OLLA) can apply to the estimated UL SINR";
      }
      leaf dmrs-additional-position {
        type uint32 {
          range "0..3";
        }
        default 2;
        description "PUSCH DMRS additional position";
      }
      leaf min-rb-size {
        type uint32 {
          range "1..275";
        }
        default 1;
        description "Minimum RB size for UE PUSCH resource allocation";
      }
      leaf max-rb-size {
        type uint32 {
          range "1..275";
        }
        default 275;
        description "Maximum RB size for UE PUSCH resource allocation";
      }
      leaf start-rb {
        type uint32 {
          range "0..275";
        }
        default 0;
        description "Start RB for resource allocation of UE PUSCHs";
      }
      leaf end-rb {
        type uint32 {
          range "0..275";
        }
        default 275;
        description "End RB for resource allocation of UE PUSCHs";
      }
      leaf enable-cl-loop-pw-control {
        type boolean;
        default false;
        description "Enable closed-loop power control for PUSCH";
      }
      leaf enable-phr-bw-adaptation {
        type boolean;
        default false;
        description "Enable bandwidth adaptation to prevent negative PHR";
      }
      leaf target-sinr {
        type decimal64 {
          fraction-digits 6;
          range "-5..30";
        }
        default 10;
        description "Target PUSCH SINR in dB";
      }
      leaf ref-path-loss {
        type decimal64 {
          fraction-digits 6;
          range "50..120";
        }
        default 70;
        description "Reference path-loss for target PUSCH SINR in dB";
      }
      leaf pl-compensation-factor {
        type decimal64 {
          fraction-digits 6;
        }
        default 1;
        description "Fractional path-loss compensation factor in PUSCH power control (legal values: {0.4, 0.5, 0.6, 0.7, 0.8, 0.9, 1.0})";
      }
      leaf enable-transform-precoding {
        type boolean;
        default false;
        description "Enable transform precoding for PUSCH.";
      }
    }
    container pucch {
      description "PUCCH parameters";
      leaf p0-nominal {
        type int32;
        default -90;
        description "Power control parameter P0 for PUCCH transmissions. Value in dBm. Valid values must be multiple of 2 and within the [-202, 24] interval. Default: -90 (must be a multiple of 2 within [-202, 24])";
      }
      leaf pucch-resource-common {
        type uint32 {
          range "0..15";
        }
        description "Index of PUCCH resource set for the common configuration";
      }
      leaf sr-period-ms {
        type decimal64 {
          fraction-digits 6;
        }
        default 20;
        description "SR period in msec (legal values: {1, 2, 2.5, 4, 5, 8, 10, 16, 20, 40, 80, 160, 320})";
      }
      leaf formats {
        type enumeration {
          enum "f0_and_f2";
          enum "f1_and_f2";
          enum "f1_and_f3";
          enum "f1_and_f4";
        }
        default "f1_and_f2";
        description "PUCCH formats combination to use. Values: {f0_and_f2, f1_and_f2, f1_and_f3, f1_and_f4}. Default: f1_and_f2";
      }
      leaf resource-set-size {
        type uint32 {
          range "1..8";
        }
        default 8;
        description "Number of PUCCH resources in each PUCCH resource set";
      }
      leaf nof-cell-res-set-configs {
        type uint32 {
          range "1..10";
        }
        default 2;
        description "Number of PUCCH Resource Set configurations that are available per cell. NOTE: the higher the number of configurations, the lower the chances UEs have to share the same PUCCH resources for HARQ-ACK.";
      }
      leaf nof-cell-sr-res {
        type uint32 {
          range "1..100";
        }
        default 8;
        description "Number of PUCCH F0/F1 resources available per cell for SR";
      }
      leaf nof-cell-csi-res {
        type uint32 {
          range "0..100";
        }
        default 8;
        description "Number of PUCCH F2/F3/F4 resources available per cell for CSI";
      }
      leaf f0-intraslot-freq-hop {
        type boolean;
        default false;
        description "Enable intra-slot frequency hopping for PUCCH F0";
      }
      leaf f1-enable-occ {
        type boolean;
        default false;
        description "Enable OCC for PUCCH F1";
      }
      leaf f1-nof-cyclic-shifts {
        type uint32;
        default 2;
        description "Number of possible cyclic shifts available for PUCCH F1 resources (legal values: {1, 2, 3, 4, 6, 12})";
      }
      leaf f1-intraslot-freq-hop {
        type boolean;
        default false;
        description "Enable intra-slot frequency hopping for PUCCH F1";
      }
      leaf f2-max-nof-rbs {
        type uint32 {
          range "1..16";
        }
        default 1;
        description "Max number of RBs for PUCCH F2 resources";
      }
      leaf f2-max-payload {
        type uint32 {
          range "4..40";
        }
        description "Min required payload capacity in bits for PUCCH F2 resources";
      }
      leaf f2-max-code-rate {
        type enumeration {
          enum "dot08";
          enum "dot15";
          enum "dot25";
          enum "dot35";
          enum "dot45";
          enum "dot60";
          enum "dot80";
        }
        default "dot35";
        description "PUCCH F2 max code rate {dot08, dot15, dot25, dot35, dot45, dot60, dot80}. Default: dot35";
      }
      leaf f2-intraslot-freq-hop {
        type boolean;
        default false;
        description "Enable intra-slot frequency hopping for PUCCH F2";
      }
      leaf f3-max-nof-rbs {
        type uint32;
        default 1;
        description "Max number of RBs for PUCCH F3 resources (legal values: {1, 2, 3, 4, 5, 6, 8, 9, 10, 12, 15, 16})";
      }
      leaf f3-max-payload {
        type uint32 {
          range "4..40";
        }
        description "Min required payload capacity in bits for PUCCH F3 resources";
      }
      leaf f3-max-code-rate {
        type enumeration {
          enum "dot08";
          enum "dot15";
          enum "dot25";
          enum "dot35";
          enum "dot45";
          enum "dot60";
          enum "dot80";
        }
        default "dot35";
        description "PUCCH F3 max code rate {dot08, dot15, dot25, dot35, dot45, dot60, dot80}. Default: dot35";
      }
      leaf f3-intraslot-freq-hop {
        type boolean;
        default false;
        description "Enable intra-slot frequency hopping for PUCCH F3";
      }
      leaf f3-additional-dmrs {
        type boolean;
        default false;
        description "Enable additional DM-RS for PUCCH F3";
      }
      leaf f3-pi2-bpsk {
        type boolean;
        default false;
        description "Enable pi/2-BPSK modulation for PUCCH F3";
      }
      leaf f4-max-code-rate {
        type enumeration {
          enum "dot08";
          enum "dot15";
          enum "dot25";
          enum "dot35";
          enum "dot45";
          enum "dot60";
          enum "dot80";
        }
        default "dot35";
        description "PUCCH F4 max code rate {dot08, dot15, dot25, dot35, dot45, dot60, dot80}. Default: dot35";
      }
      leaf f4-intraslot-freq-hop {
        type boolean;
        default false;
        description "Enable intra-slot frequency hopping for PUCCH F4";
      }
      leaf f4-additional-dmrs {
        type boolean;
        default false;
        description "Enable additional DM-RS for PUCCH F4";
      }
      leaf f4-pi2-bpsk {
        type boolean;
        default false;
        description "Enable pi/2-BPSK modulation for PUCCH F4";
      }
      leaf f4-occ-length {
        type uint32;
        default 2;
        description "OCC length for PUCCH F4 (legal values: {2, 4})";
      }
      leaf f4-enable-occ {
        type boolean;
        default false;
        description "Enable OCC multiplexing for PUCCH F4";
      }
      leaf min-k1 {
        type uint32 {
          range "1..4";
        }
        default 4;
        description "Minimum value of K1 (difference in slots between PDSCH and HARQ-ACK). Lower k1 values will reduce latency, but place a stricter requirement on the UE decode latency.";
      }
      leaf max-consecutive-kos {
        type uint32;
        default 100;
        description "Maximum number of consecutive undecoded PUCCH F2 for CSI before an Radio Link Failure is reported";
      }
      leaf enable-cl-loop-pw-control {
        type boolean;
        default false;
        description "Enable closed-loop power control for PUCCH";
      }
      leaf target-sinr-f0 {
        type decimal64 {
          fraction-digits 6;
          range "-10..20";
        }
        default 10;
        description "Target PUCCH F0 SINR in dB";
      }
      leaf target-sinr-f2 {
        type decimal64 {
          fraction-digits 6;
          range "-10..20";
        }
        default 6;
        description "Target PUCCH F2 SINR in dB";
      }
      leaf target-sinr-f3 {
        type decimal64 {
          fraction-digits 6;
          range "-15..10";
        }
        default 1;
        description "Target PUCCH F3 SINR in dB";
      }
    }
    container srs {
      description "SRS parameters";
      leaf type-enabled {
        type enumeration {
          enum "disabled";
          enum "periodic";
          enum "aperiodic";
        }
        default "disabled";
        description "Enable/disable SRS and set resource type";
      }
      leaf period-ms {
        type decimal64 {
          fraction-digits 6;
        }
        default 20;
        description "SRS period in ms. For aperiodic SRS, it indicates a tentative timing, and should not be interpreted as a precise period. The SRS period needs to be compatible with the subcarrier spacing (legal values: {1, 2, 2.5, 4, 5, 8, 10, 16, 20, 32, 40, 64, 80, 160, 320, 640, 1280, 2560})";
      }
      leaf max-nof-sym-per-slot {
        type uint32 {
          range "1..6";
        }
        default 2;
        description "Number of symbols for UL slot that are reserved for the SRS cell resources";
      }
      leaf nof-sym-per-resource {
        type uint32;
        default 1;
        description "Number of symbols per SRS resource (legal values: {1, 2, 4})";
      }
      leaf c-srs {
        type uint32 {
          range "0..63";
        }
        description "C_SRS parameter for SRS. If not set, it's computed automatically from the cell parameters";
      }
      leaf freq-domain-shift {
        type uint32 {
          range "0..268";
        }
        default 0;
        description "SRS frequency domain shift. Only applies if c_srs is set";
      }
      leaf tx-comb {
        type uint32;
        default 4;
        description "SRS TX comb size (legal values: {2, 4})";
      }
      leaf cyclic-shift-reuse {
        type uint32;
        default 1;
        description "SRS cyclic shift reuse factor. It needs to be compatible with the TX comb and number of UL antenna ports (legal values: {1, 2, 3, 4, 6})";
      }
      leaf sequence-id-reuse {
        type uint32;
        default 1;
        description "Enable the reuse of SRS sequence id with the set reuse factor (legal values: {1, 2, 3, 5, 6, 10, 15, 30})";
      }
      leaf p0 {
        type int32;
        default -84;
        description "P0 value for SRS. Value in dBm. Valid values must be multiple of 2 and within the [-202, 24] interval. Default: -84 (must be a multiple of 2 within [-202, 24])";
      }
    }
    container prach {
      description "PRACH parameters";
      leaf prach-config-index {
        type uint32 {
          range "0..255";
        }
        description "PRACH configuration index. If not set, the value is derived, so that the PRACH fits in an UL slot";
      }
      leaf prach-root-sequence-index {
        type uint32 {
          range "0..837";
        }
        default 1;
        description "PRACH root sequence index. NOTE: values: [0, 837] for PRACH format 0, 1, 2, 3. [0, 137] for other formats";
      }
      leaf zero-correlation-zone {
        type uint32 {
          range "0..15";
        }
        default 0;
        description "Zero correlation zone index";
      }
      leaf fixed-msg3-mcs {
        type uint32 {
          range "0..28";
        }
        default 0;
        description "Fixed message 3 MCS";
      }
      leaf max-msg3-harq-retx {
        type uint32 {
          range "0..4";
        }
        default 4;
        description "Maximum number of message 3 HARQ retransmissions";
      }
      leaf total-nof-ra-preambles {
        type uint32 {
          range "1..64";
        }
        default 64;
        description "Number of different contention-based PRACH preambles per occasion. If less than 64 preambles are used, the remaining preambles can be used for contention-free PRACHs";
      }
      leaf cfra-enabled {
        type boolean;
        default false;
        description "Whether to enable Contention-free Random Access (CFRA). If enabled, the total_nof_ra_preambles must be lower than 64";
      }
      leaf prach-frequency-start {
        type uint32 {
          range "0..274";
        }
        description "PRACH message frequency offset in PRBs. NOTE: When setting this parameter, it's up to user the ensure the PRACH opportunities do not overlap with the PUCCH resources";
      }
      leaf preamble-rx-target-pw {
        type int32;
        default -100;
        description "Target power level at the network receiver side, in dBm (must be a multiple of 2 within [-202, -60])";
      }
      leaf preamble-trans-max {
        type uint8;
        default 7;
        description "Max number of RA preamble transmissions performed before declaring a failure (legal values: {3, 4, 5, 6, 7, 8, 10, 20, 50, 100, 200})";
      }
      leaf power-ramping-step-db {
        type uint8;
        default 4;
        description "Power ramping steps for PRACH (legal values: {0, 2, 4, 6})";
      }
      leaf-list ports {
        type uint8;
        description "List of antenna ports";
      }
      leaf nof-ssb-per-ro {
        type uint8;
        default 3;
        description "Number of SSBs per RACH occasion (legal values: {1})";
      }
      leaf nof-cb-preambles-per-ssb {
        type uint8 {
          range "1..64";
        }
        default 64;
        description "Number of Contention Based preambles per SSB";
      }
      leaf ra-resp-window {
        type uint32;
        description "RA-Response window length in number of slots. (legal values: {1, 2, 4, 8, 10, 20, 40, 80})";
      }
      leaf nof-prach-guardbands-rbs {
        type uint32 {
          range "1..10";
        }
        default 3;
        description "Number of RBs that are used as guardband on each side of the PRACH RBs interval for short PRACH formats.";
      }
      list slice-based-ra-prioritization {
        // WARNING: no key designated; YANG list requires `key`. Use .key("...") at declaration.
        description "List of configurations for slice-based RA prioritization";
        leaf power-ramp-step-high-priority {
          type uint32;
          default 0;
          description "Power ramping step applied for prioritized random access procedure [dB]. (legal values: {0, 2, 4, 6})";
        }
        leaf scaling-factor-bi {
          type decimal64 {
            fraction-digits 6;
          }
          description "Scaling factor for backoff indicator (BI) for the prioritized RA procedure. (legal values: {0.0, 0.25, 0.5, 0.75})";
        }
        leaf-list nsag-ids {
          type uint8;
          description "NSAGs associated with this prioritized RA configuration.";
        }
      }
      container two-step {
        description "Two-step RACH (MsgA/MsgB) configuration";
        leaf cb-preambles-per-ssb-per-shared-ro {
          type uint8 {
            range "1..60";
          }
          default 4;
          description "Number of CB preambles per SSB per shared RACH occasion for 2-step RA";
        }
        leaf msgA-rsrp-thres-dbm {
          type int32 {
            range "-156..-29";
          }
          default -100;
          description "RSRP threshold in dBm above which the UE selects 2-step RA over 4-step RA";
        }
        leaf msgB-response-window-slots {
          type uint32;
          default 40;
          description "MsgB response window length in slots (legal values: {1, 2, 4, 8, 10, 20, 40, 80, 160, 320})";
        }
        leaf td-offset {
          type uint8 {
            range "1..32";
          }
          default 1;
          description "Time-domain offset in slots from the PRACH slot to the MsgA PUSCH slot";
        }
        leaf pusch-td-res-index {
          type uint8;
          default 0;
          description "Index into the PUSCH-TimeDomainAllocationResource table for MsgA PUSCH scheduling";
        }
        leaf mcs {
          type uint8 {
            range "0..28";
          }
          default 0;
          description "MCS index for MsgA PUSCH transmission";
        }
        leaf nof-prbs-per-msgA-po {
          type uint8 {
            range "1..32";
          }
          default 3;
          description "Number of PRBs per MsgA PUSCH occasion";
        }
        leaf prb-start {
          type uint32;
          default 0;
          description "Frequency offset in PRBs of the lowest MsgA PUSCH occasion from PRB 0";
        }
        leaf po-fdm {
          type uint8;
          default 1;
          description "Number of MsgA PUSCH occasions FDMed in one time instance (legal values: {1, 2, 4, 8})";
        }
      }
    }
    container tdd-ul-dl-cfg {
      description "TDD UL DL configuration parameters";
      leaf dl-ul-tx-period {
        type uint32 {
          range "2..80";
        }
        default 10;
        description "TDD pattern periodicity in slots. The combination of this value and the chosen numerology must lead to a TDD periodicity of 0.5, 0.625, 1, 1.25, 2, 2.5, 3, 4, 5 or 10 milliseconds.";
      }
      leaf nof-dl-slots {
        type uint32 {
          range "0..80";
        }
        default 6;
        description "TDD pattern nof. consecutive full DL slots";
      }
      leaf nof-dl-symbols {
        type uint32 {
          range "0..13";
        }
        default 8;
        description "TDD pattern nof. DL symbols at the beginning of the slot following full DL slots";
      }
      leaf nof-ul-slots {
        type uint32 {
          range "0..80";
        }
        default 3;
        description "TDD pattern nof. consecutive full UL slots";
      }
      leaf nof-ul-symbols {
        type uint32 {
          range "0..13";
        }
        default 0;
        description "TDD pattern nof. UL symbols at the end of the slot preceding the first full UL slot";
      }
      container pattern2 {
        description "TDD UL DL pattern2 configuration parameters";
        leaf dl-ul-tx-period {
          type uint32 {
            range "2..80";
          }
          default 10;
          description "TDD pattern periodicity in slots. The combination of this value and the chosen numerology must lead to a TDD periodicity of 0.5, 0.625, 1, 1.25, 2, 2.5, 3, 4, 5 or 10 milliseconds.";
        }
        leaf nof-dl-slots {
          type uint32 {
            range "0..80";
          }
          default 6;
          description "TDD pattern nof. consecutive full DL slots";
        }
        leaf nof-dl-symbols {
          type uint32 {
            range "0..13";
          }
          default 8;
          description "TDD pattern nof. DL symbols at the beginning of the slot following full DL slots";
        }
        leaf nof-ul-slots {
          type uint32 {
            range "0..80";
          }
          default 3;
          description "TDD pattern nof. consecutive full UL slots";
        }
        leaf nof-ul-symbols {
          type uint32 {
            range "0..13";
          }
          default 0;
          description "TDD pattern nof. UL symbols at the end of the slot preceding the first full UL slot";
        }
      }
    }
    container paging {
      description "Paging parameters";
      leaf pg-search-space-id {
        type uint32;
        default 1;
        description "SearchSpace to use for Paging (legal values: {0, 1})";
      }
      leaf default-pg-cycle-in-rf {
        type uint32;
        default 128;
        description "Default Paging cycle in nof. Radio Frames (legal values: {32, 64, 128, 256})";
      }
      leaf nof-pf-per-paging-cycle {
        type enumeration {
          enum "oneT";
          enum "halfT";
          enum "quarterT";
          enum "oneEighthT";
          enum "oneSixteethT";
        }
        default "oneT";
        description "Number of paging frames per DRX cycle {oneT, halfT, quarterT, oneEighthT, oneSixteethT}. Default: oneT";
      }
      leaf pf-offset {
        type uint32;
        default 0;
        description "Paging frame offset";
      }
      leaf nof-po-per-pf {
        type uint32;
        default 1;
        description "Number of paging occasions per paging frame (legal values: {1, 2, 4})";
      }
      leaf edrx-enabled {
        type boolean;
        default false;
        description "Enable eDRX";
      }
    }
    container csi {
      description "CSI-Meas parameters";
      leaf csi-rs-enabled {
        type boolean;
        default true;
        description "Enable CSI-RS resources and CSI reporting";
      }
      leaf csi-rs-period {
        type uint32;
        default 20;
        description "CSI-RS period in milliseconds (legal values: {10, 20, 40, 80})";
      }
      leaf report-type {
        type enumeration {
          enum "periodic";
          enum "aperiodic";
        }
        default "periodic";
        description "Type of CSI reporting configuration to use";
      }
      leaf meas-csi-rs-slot-offset {
        type uint32;
        description "Slot offset of first CSI-RS resource used for measurement";
      }
      leaf tracking-csi-rs-slot-offset {
        type uint32;
        description "Slot offset of first CSI-RS resource used for tracking";
      }
      leaf zp-csi-rs-slot-offset {
        type uint32;
        description "Slot offset of the ZP CSI-RS resources";
      }
      leaf pwr-ctrl-offset {
        type int32 {
          range "-8..15";
        }
        default 0;
        description "powerControlOffset, Power offset of PDSCH RE to NZP CSI-RS RE in dB";
      }
    }
    container scheduler {
      description "Scheduler parameters";
      leaf nof-preselected-newtx-ues {
        type uint32 {
          range "1..8192";
        }
        default 1024;
        description "Number of UEs pre-selected for potential newTx allocations in a slot. The scheduling policy will only be applied to the pre-selected UEs.";
      }
      container policy {
        description "Scheduler policy configuration. By default, time-domain QoS-aware policy is used.";
        container qos-sched {
          description "Time-domain QoS-aware policy configuration";
          leaf combine-function {
            type enumeration {
              enum "gbr_prioritized";
              enum "geometric_mean";
            }
            default "gbr_prioritized";
            description "QoS-aware scheduler policy weight combining function";
          }
          leaf pf-fairness-coeff {
            type decimal64 {
              fraction-digits 6;
            }
            default 2;
            description "Fairness Coefficient to use in Proportional Fair (PF) weight";
          }
          leaf prio-enabled {
            type boolean;
            default true;
            description "Whether to take into account the QoS Flow priority in QoS-aware scheduling";
          }
          leaf pdb-enabled {
            type boolean;
            default true;
            description "Whether to take into account the QoS Flow Packet Delay Budget (PDB) in QoS-aware scheduling";
          }
          leaf gbr-enabled {
            type boolean;
            default true;
            description "Whether to take into account the QoS Flow Guaranteed Bit Rate (GBR) in QoS-aware scheduling";
          }
        }
        container rr-sched {
          description "Time-domain Round-robin policy configuration";
        }
      }
    }
    container ta {
      description "Time Advance (TA) parameters";
      leaf ta-measurement-slot-period {
        type uint32;
        default 80;
        description "Measurements periodicity in number of slots over which the new Timing Advance Command is computed";
      }
      leaf ta-measurement-slot-prohibit-period {
        type uint32 {
          range "0..10000";
        }
        default 0;
        description "Delay in number of slots between issuing the TA_CMD and starting TA measurements.";
      }
      leaf ta-cmd-offset-threshold {
        type int32 {
          range "-1..31";
        }
        default 1;
        description "Timing Advance Command (T_A) offset threshold above which Timing Advance Command is triggered. If set to less than zero, issuing of TA Command is disabled";
      }
      leaf ta-target {
        type decimal64 {
          fraction-digits 6;
          range "-30..30";
        }
        default 1;
        description "Timing Advance target in units of TA";
      }
      leaf ta-update-measurement-ul-sinr-threshold {
        type decimal64 {
          fraction-digits 6;
        }
        default 0;
        description "UL SINR threshold (in dB) above which reported N_TA update measurement is considered valid";
      }
      leaf ta-outlier-detection-zscore-threshold {
        type decimal64 {
          fraction-digits 6;
          range "0..5";
        }
        default 1.75;
        description "Z-score threshold for outlier detection in N_TA measurements. Controls the sensitivity of the outlier detection algorithm. A lower value makes the filter more aggressive (rejects more measurements), while a higher value makes it more permissive. Typical values range from 1.5 to 3.0. Setting to 0.0 disables outlier detection.";
      }
    }
    container drx {
      description "DRX parameters";
      leaf on-duration-timer {
        type uint32;
        default 10;
        description "Minimum duration in milliseconds that the UE stays in active mode, when DRX is configured. (legal values: drx_helper::valid_on_duration_timer_values())";
      }
      leaf inactivity-timer {
        type uint32;
        default 0;
        description "Duration in milliseconds that the UE stays active after PDCCH reception, when DRX is configured. (legal values: drx_helper::valid_inactivity_timer_values())";
      }
      leaf retx-timer-dl {
        type uint32;
        default 0;
        description "Maximum duration in slots until a DL ReTX is received by the UE, when DRX is configured. (legal values: drx_helper::valid_retx_timer_values())";
      }
      leaf retx-timer-ul {
        type uint32;
        default 0;
        description "Maximum duration in slots until a grant for UL ReTX is received by the UE, when DRX is configured. (legal values: drx_helper::valid_retx_timer_values())";
      }
      leaf long-cycle {
        type uint32;
        default 0;
        description "Duration in milliseconds between UE DRX long cycles. The value 0 is used to disable DRX (legal values: drx_helper::valid_long_cycle_values() ∪ {0})";
      }
    }
    list slicing {
      // WARNING: no key designated; YANG list requires `key`. Use .key("...") at declaration.
      description "Network slicing configuration";
      leaf sst {
        type uint8 {
          range "0..255";
        }
        default 0;
        description "Slice Service Type";
      }
      leaf sd {
        type uint32 {
          range "0..16777215";
        }
        default 16777215;
        description "Service Differentiator";
      }
      container sched-cfg {
        description "Slice scheduling configuration";
        leaf min-prb-policy-ratio {
          type uint32 {
            range "0..100";
          }
          default 0;
          description "Minimum percentage of PRBs to be allocated to the slice";
        }
        leaf max-prb-policy-ratio {
          type uint32 {
            range "1..100";
          }
          default 100;
          description "Maximum percentage of PRBs to be allocated to the slice";
        }
        leaf ded-prb-policy-ratio {
          type uint32 {
            range "1..100";
          }
          default 0;
          description "Dedicated percentage of PRBs to be allocated to the slice";
        }
        leaf priority {
          type uint32 {
            range "0..254";
          }
          default 0;
          description "Slice priority";
        }
        container policy {
          description "Scheduler policy configuration for the slice. If not specified, the policy configured for the cell is used";
          container qos-sched {
            description "Time-domain QoS-aware policy configuration";
            leaf combine-function {
              type enumeration {
                enum "gbr_prioritized";
                enum "geometric_mean";
              }
              default "gbr_prioritized";
              description "QoS-aware scheduler policy weight combining function";
            }
            leaf pf-fairness-coeff {
              type decimal64 {
                fraction-digits 6;
              }
              default 2;
              description "Fairness Coefficient to use in Proportional Fair (PF) weight";
            }
            leaf prio-enabled {
              type boolean;
              default true;
              description "Whether to take into account the QoS Flow priority in QoS-aware scheduling";
            }
            leaf pdb-enabled {
              type boolean;
              default true;
              description "Whether to take into account the QoS Flow Packet Delay Budget (PDB) in QoS-aware scheduling";
            }
            leaf gbr-enabled {
              type boolean;
              default true;
              description "Whether to take into account the QoS Flow Guaranteed Bit Rate (GBR) in QoS-aware scheduling";
            }
          }
          container rr-sched {
            description "Time-domain Round-robin policy configuration";
          }
        }
      }
    }
    container ntn {
      description "NTN configuration";
      leaf cell-specific-koffset {
        type int64 {
          range "1..1023";
        }
        default 0;
        description "Cell-specific k-offset to be used for NTN [ms].";
      }
      leaf ntn-ul-sync-validity-dur {
        type uint32;
        description "An UL sync validity duration (legal values: {5, 10, 15, 20, 25, 30, 35, 40, 45, 50, 55, 60, 120, 180, 240, 900})";
      }
      container epoch-time {
        description "Epoch time for the NTN assistance information";
        leaf sfn {
          type uint32 {
            range "0..1023";
          }
          default 0;
          description "SFN Part";
        }
        leaf subframe-number {
          type uint32 {
            range "0..9";
          }
          default 0;
          description "Sub-frame number Part";
        }
      }
      container ta-info {
        description "TA Info for the NTN assistance information";
        leaf ta-common {
          type decimal64 {
            fraction-digits 6;
            range "0..270730";
          }
          default 0;
          description "TA common";
        }
        leaf ta-common-drift {
          type decimal64 {
            fraction-digits 6;
            range "-51.4606..51.4606";
          }
          default 0;
          description "Drift rate of the common TA";
        }
        leaf ta-common-drift-variant {
          type decimal64 {
            fraction-digits 6;
            range "0..0.57898";
          }
          default 0;
          description "Drift rate variation of the common TA";
        }
        leaf ta-common-offset {
          type decimal64 {
            fraction-digits 6;
            range "0..10000";
          }
          default 0;
          description "Constant offset added to TA common";
        }
      }
      container ephemeris-info-ecef {
        description "Ephermeris information of the satellite in ecef coordinates";
        leaf pos-x {
          type decimal64 {
            fraction-digits 6;
            range "-43620761.6..43620759.3";
          }
          default 0;
          description "X Position of the satellite [m]";
        }
        leaf pos-y {
          type decimal64 {
            fraction-digits 6;
            range "-43620761.6..43620759.3";
          }
          default 0;
          description "Y Position of the satellite [m]";
        }
        leaf pos-z {
          type decimal64 {
            fraction-digits 6;
            range "-43620761.6..43620759.3";
          }
          default 0;
          description "Z Position of the satellite [m]";
        }
        leaf vel-x {
          type decimal64 {
            fraction-digits 6;
            range "-7864.32..7864.26";
          }
          default 0;
          description "X Velocity of the satellite [m/s]";
        }
        leaf vel-y {
          type decimal64 {
            fraction-digits 6;
            range "-7864.32..7864.26";
          }
          default 0;
          description "Y Velocity of the satellite [m/s]";
        }
        leaf vel-z {
          type decimal64 {
            fraction-digits 6;
            range "-7864.32..7864.26";
          }
          default 0;
          description "Z Velocity of the satellite [m/s]";
        }
      }
      container ephemeris-orbital {
        description "Ephermeris information of the satellite in orbital coordinates";
        leaf semi-major-axis {
          type decimal64 {
            fraction-digits 6;
            range "6500000..42998632.07";
          }
          default 0;
          description "Semi-major axis of the satellite [m]";
        }
        leaf eccentricity {
          type decimal64 {
            fraction-digits 6;
            range "0..0.01500510825";
          }
          default 0;
          description "Eccentricity of the satellite [-]";
        }
        leaf periapsis {
          type decimal64 {
            fraction-digits 6;
            range "0..6.28407400155";
          }
          default 0;
          description "Periapsis of the satellite [rad]";
        }
        leaf longitude {
          type decimal64 {
            fraction-digits 6;
            range "0..6.28407400155";
          }
          default 0;
          description "Longitude of the satellites angle of ascending node [rad]";
        }
        leaf inclination {
          type decimal64 {
            fraction-digits 6;
            range "-1.57101850624..1.57101848283";
          }
          default 0;
          description "Inclination of the satellite [rad]";
        }
        leaf mean-anomaly {
          type decimal64 {
            fraction-digits 6;
            range "0..6.28407400155";
          }
          default 0;
          description "Mean anomaly of the satellite [rad]";
        }
      }
    }
    container rlm {
      description "Radio Link Monitoring parameters";
      leaf rlm-resource-type {
        type enumeration {
          enum "default_type";
          enum "ssb";
          enum "csi_rs";
          enum "ssb_and_csi_rs";
        }
        default "default_type";
        description "Radio Link Monitoring resource detection type {default_type, ssb, csi_rs, ssb_and_csi_rs}. Default: default_type";
      }
    }
  }
  list qos {
    key "five-qi";
    description "Configures RLC and PDCP radio bearers on a per 5QI basis.";
    leaf five-qi {
      type uint16 {
        range "0..255";
      }
      default 9;
      description "5QI";
    }
    container rlc {
      description "RLC parameters";
      leaf mode {
        type string;
        default "am";
        description "RLC mode";
      }
      container um-bidir {
        description "UM parameters";
        container tx {
          description "UM TX parameters";
          leaf sn {
            type uint16;
            default 0;
            description "RLC UM TX SN";
          }
          leaf queue-size {
            type uint32;
            default 0;
            description "RLC UM TX SDU queue limit in PDUs";
          }
          leaf queue-bytes {
            type uint32;
            default 0;
            description "RLC UM TX SDU queue limit in bytes";
          }
        }
        container rx {
          description "UM TX parameters";
          leaf sn {
            type uint16;
            default 0;
            description "RLC UM RX SN";
          }
          leaf t-reassembly {
            type int32;
            default 0;
            description "RLC UM t-Reassembly";
          }
        }
      }
      container am {
        description "AM parameters";
        container tx {
          description "AM TX parameters";
          leaf sn {
            type uint16;
            default 0;
            description "RLC AM TX SN size";
          }
          leaf t-poll-retransmit {
            type int32;
            default 0;
            description "RLC AM TX t-PollRetransmit (ms)";
          }
          leaf max-retx-threshold {
            type uint32;
            default 0;
            description "RLC AM max retx threshold";
          }
          leaf poll-pdu {
            type int32;
            default 0;
            description "RLC AM TX PollPdu";
          }
          leaf poll-byte {
            type int32;
            default 0;
            description "RLC AM TX PollByte";
          }
          leaf max-window {
            type uint32;
            default 0;
            description "Non-standard parameter that limits the tx window size. Can be used for limiting memory usage with large windows. 0 means no limits other than the SN size (i.e. 2^[sn_size-1]).";
          }
          leaf queue-size {
            type uint32;
            default 4096;
            description "RLC AM TX SDU queue size in PDUs";
          }
          leaf queue-bytes {
            type uint32;
            default 6172672;
            description "RLC AM TX SDU queue size in bytes";
          }
        }
        container rx {
          description "AM RX parameters";
          leaf sn {
            type uint16;
            default 0;
            description "RLC AM RX SN";
          }
          leaf t-reassembly {
            type int32;
            default 0;
            description "RLC AM RX t-Reassembly";
          }
          leaf t-status-prohibit {
            type int32;
            default 0;
            description "RLC AM RX t-StatusProhibit";
          }
          leaf max-sn-per-status {
            type uint32;
            default 0;
            description "RLC AM RX status SN limit";
          }
        }
      }
    }
    container f1u-du {
      description "F1-U parameters at DU side";
      leaf backoff-timer {
        type int32;
        default 0;
        description "F1-U backoff timer (ms)";
      }
      leaf ul-buffer-size {
        type uint32;
        default 0;
        description "F1-U handover buffer size";
      }
    }
  }
  list srbs {
    // WARNING: no key designated; YANG list requires `key`. Use .key("...") at declaration.
    description "Configures signaling radio bearers.";
    leaf srb-id {
      type uint32;
      default 0;
      description "SRB Id (legal values: {1, 2})";
    }
    container rlc {
      description "RLC parameters";
      container tx {
        description "AM TX parameters";
        leaf sn {
          type uint16;
          default 0;
          description "RLC AM TX SN size";
        }
        leaf t-poll-retransmit {
          type int32;
          default 0;
          description "RLC AM TX t-PollRetransmit (ms)";
        }
        leaf max-retx-threshold {
          type uint32;
          default 0;
          description "RLC AM max retx threshold";
        }
        leaf poll-pdu {
          type int32;
          default 0;
          description "RLC AM TX PollPdu";
        }
        leaf poll-byte {
          type int32;
          default 0;
          description "RLC AM TX PollByte";
        }
        leaf max-window {
          type uint32;
          default 0;
          description "Non-standard parameter that limits the tx window size. Can be used for limiting memory usage with large windows. 0 means no limits other than the SN size (i.e. 2^[sn_size-1]).";
        }
        leaf queue-size {
          type uint32;
          default 4096;
          description "RLC AM TX SDU queue size in PDUs";
        }
        leaf queue-bytes {
          type uint32;
          default 6172672;
          description "RLC AM TX SDU queue size in bytes";
        }
      }
      container rx {
        description "AM RX parameters";
        leaf sn {
          type uint16;
          default 0;
          description "RLC AM RX SN";
        }
        leaf t-reassembly {
          type int32;
          default 0;
          description "RLC AM RX t-Reassembly";
        }
        leaf t-status-prohibit {
          type int32;
          default 0;
          description "RLC AM RX t-StatusProhibit";
        }
        leaf max-sn-per-status {
          type uint32;
          default 0;
          description "RLC AM RX status SN limit";
        }
      }
    }
  }
  container test-mode {
    description "Test mode configuration";
    container test-ue {
      description "automatically created UE for testing purposes";
      leaf rnti {
        type uint16 {
          range "0..65519";
        }
        default 0;
        description "C-RNTI (0x0 if not configured)";
      }
      leaf nof-ues {
        type uint16 {
          range "1..8192";
        }
        default 1;
        description "Number of test UE(s) to create.";
      }
      leaf ue-creation-stagger-slots {
        type uint32 {
          range "0..10240";
        }
        default 10;
        description "Number of slots between consecutive test mode UE creations";
      }
      leaf auto-ack-indication-delay {
        type uint32;
        description "Delay before the UL and DL HARQs are automatically ACKed. This feature should only be used if the UL PHY is not operational";
      }
      leaf attach-detach-duration-ms {
        type uint32 {
          range "100..10000";
        }
        description "Duration in milliseconds of active traffic after all UEs are established before they are released and recreated. When set, UEs cycle indefinitely through attach, traffic, and detach. Unset disables cycling.";
      }
      leaf attach-detach-guard-duration-ms {
        type uint32 {
          range "100..60000";
        }
        default 1000;
        description "Guard period duration in milliseconds between a release cycle and the next creation cycle.";
      }
      leaf pdsch-active {
        type boolean;
        default true;
        description "PDSCH enabled";
      }
      leaf pusch-active {
        type boolean;
        default true;
        description "PUSCH enabled";
      }
      leaf cqi {
        type uint32 {
          range "1..15";
        }
        default 15;
        description "Channel Quality Information (CQI) to be forwarded to test UE.";
      }
      leaf ri {
        type uint32 {
          range "1..4";
        }
        default 1;
        description "Rank Indicator (RI) to be forwarded to test UE.";
      }
      leaf pmi {
        type uint32 {
          range "0..3";
        }
        default 0;
        description "Precoder Matrix Indicator (PMI) to be forwarded to test UE.";
      }
      leaf i-1-1 {
        type uint32 {
          range "0..7";
        }
        default 0;
        description "Precoder Matrix codebook index \"i_1_1\" to be forwarded to test UE, in the case of more than 2 antennas.";
      }
      leaf i-1-3 {
        type uint32 {
          range "0..1";
        }
        default 0;
        description "Precoder Matrix codebook index \"i_1_3\" to be forwarded to test UE, in the case of more than 2 antennas.";
      }
      leaf i-2 {
        type uint32 {
          range "0..3";
        }
        default 0;
        description "Precoder Matrix codebook index \"i_2\" to be forwarded to test UE, in the case of more than 2 antennas.";
      }
    }
  }
  container e2 {
    description "E2 parameters";
    leaf enable-du-e2 {
      type boolean;
      default false;
      description "Enable DU E2 agent";
    }
    leaf-list addrs {
      type string;
      description "RIC addresses to be used for E2 interface. Multiple addresses can be specified for SCTP multi-homing";
    }
    leaf port {
      type uint16 {
        range "20000..40000";
      }
      default 36421;
      description "RIC port";
    }
    leaf-list bind-addrs {
      type string;
      description "Local bind addresses to be used for E2 interface. Multiple addresses can be specified for SCTP multi-homing. If left empty, implicit bind is performed";
    }
    leaf e2sm-kpm-enabled {
      type boolean;
      default false;
      description "Enable KPM service module";
    }
    leaf e2sm-rc-enabled {
      type boolean;
      default false;
      description "Enable RC service module";
    }
    leaf e2sm-ccc-enabled {
      type boolean;
      default false;
      description "Enable CCC service module";
    }
    uses sctp-socket;
  }
  container expert-phy {
    description "Expert physical layer configuration";
    leaf max-proc-delay {
      type uint32 {
        range "1..30";
      }
      default 5;
      description "Maximum allowed DL processing delay in slots.";
    }
    leaf pusch-dec-max-iterations {
      type uint32;
      default 6;
      description "Maximum number of PUSCH LDPC decoder iterations";
    }
    leaf pusch-dec-enable-early-stop {
      type boolean;
      default true;
      description "Enables PUSCH LDPC decoder early stop";
    }
    leaf pusch-decoder-force-decoding {
      type boolean;
      default false;
      description "Forces PUSCH LDPC decoder to decode always";
    }
    leaf pusch-sinr-calc-method {
      type enumeration {
        enum "channel_estimator";
        enum "post_equalization";
        enum "evm";
      }
      default "post_equalization";
      description "PUSCH SINR calculation method: channel_estimator, post_equalization and evm.";
    }
    leaf pusch-channel-estimator-fd-strategy {
      type enumeration {
        enum "filter";
        enum "mean";
        enum "none";
      }
      default "filter";
      description "PUSCH channel estimator frequency-domain smoothing strategy: filter, mean and none.";
    }
    leaf pusch-channel-estimator-td-strategy {
      type enumeration {
        enum "average";
        enum "interpolate";
      }
      default "average";
      description "PUSCH channel estimator time-domain strategy: average and interpolate.";
    }
    leaf pusch-channel-estimator-cfo-compensation {
      type boolean;
      default true;
      description "PUSCH channel estimator CFO compensation.";
    }
    leaf pusch-channel-equalizer-algorithm {
      type enumeration {
        enum "zf";
        enum "mmse";
      }
      default "zf";
      description "PUSCH channel equalizer algorithm: zf and mmse.";
    }
    leaf max-request-headroom-slots {
      type uint32 {
        range "0..30";
      }
      default 0;
      description "Maximum request headroom size in slots.";
    }
    leaf allow-request-on-empty-uplink-slot {
      type boolean;
      default false;
      description "Generates an uplink request in an uplink slot with no PUCCH/PUSCH/SRS PDUs";
    }
    leaf enable-phy-tap {
      type boolean;
      default false;
      description "Enables or disables the PHY tap plugin if it is present while building the application.";
    }
    leaf phy-tap-arguments {
      type string;
      default "";
      description "PHY tap plugin argument string passed during construction.";
    }
  }
  container ru-ofh {
    description "Open Fronthaul Radio Unit configuration";
    leaf gps-alpha {
      type uint32 {
        range "0..12288000";
      }
      default 0;
      description "GPS Alpha";
    }
    leaf gps-beta {
      type int32 {
        range "-32768..32767";
      }
      default 0;
      description "GPS Beta";
    }
    container base-cell {
      description "Base cell parameters that propagate to each entry in --cells";
      leaf t1a-max-cp-dl {
        type int64 {
          range "0..1960";
        }
        default 500;
        description "T1a maximum value for downlink Control-Plane";
      }
      leaf t1a-min-cp-dl {
        type int64 {
          range "0..1960";
        }
        default 258;
        description "T1a minimum value for downlink Control-Plane";
      }
      leaf t1a-max-cp-ul {
        type int64 {
          range "0..1960";
        }
        default 500;
        description "T1a maximum value for uplink Control-Plane";
      }
      leaf t1a-min-cp-ul {
        type int64 {
          range "0..1960";
        }
        default 285;
        description "T1a minimum value for uplink Control-Plane";
      }
      leaf t1a-max-up {
        type int64 {
          range "0..1960";
        }
        default 300;
        description "T1a maximum value for User-Plane";
      }
      leaf t1a-min-up {
        type int64 {
          range "0..1960";
        }
        default 85;
        description "T1a minimum value for User-Plane";
      }
      leaf ta4-max {
        type int64 {
          range "0..1960";
        }
        default 500;
        description "Ta4 maximum value for User-Plane";
      }
      leaf ta4-min {
        type int64 {
          range "0..1960";
        }
        default 85;
        description "Ta4 minimum value for User-Plane";
      }
      leaf is-prach-cp-enabled {
        type boolean;
        default true;
        description "PRACH Control-Plane enabled flag";
      }
      leaf ignore-ecpri-seq-id {
        type boolean;
        default false;
        description "Ignore eCPRI sequence id field value";
      }
      leaf ignore-ecpri-payload-size {
        type boolean;
        default false;
        description "Ignore eCPRI payload size field value";
      }
      leaf ignore-prach-start-symbol {
        type boolean;
        default false;
        description "Ignore the start symbol field in the PRACH U-Plane packets";
      }
      leaf log-lates-as-warnings {
        type boolean;
        default true;
        description "Log late events as warnings";
      }
      leaf warn-unreceived-ru-frames {
        type enumeration {
          enum "never";
          enum "always";
          enum "after_traffic_detection";
        }
        default "after_traffic_detection";
        description "Warn of unreceived Radio Unit frames";
      }
      leaf compr-method-ul {
        type enumeration {
          enum "none";
          enum "bfp";
          enum "bfp selective";
          enum "block scaling";
          enum "mu law";
          enum "modulation";
          enum "modulation selective";
        }
        default "bfp";
        description "Uplink compression method";
      }
      leaf compr-bitwidth-ul {
        type uint32 {
          range "1..16";
        }
        default 9;
        description "Uplink compression bit width";
      }
      leaf compr-method-dl {
        type enumeration {
          enum "none";
          enum "bfp";
          enum "bfp selective";
          enum "block scaling";
          enum "mu law";
          enum "modulation";
          enum "modulation selective";
        }
        default "bfp";
        description "Downlink compression method";
      }
      leaf compr-bitwidth-dl {
        type uint32 {
          range "1..16";
        }
        default 9;
        description "Downlink compression bit width";
      }
      leaf compr-method-prach {
        type enumeration {
          enum "none";
          enum "bfp";
          enum "bfp selective";
          enum "block scaling";
          enum "mu law";
          enum "modulation";
          enum "modulation selective";
        }
        default "bfp";
        description "PRACH compression method";
      }
      leaf compr-bitwidth-prach {
        type uint32 {
          range "1..16";
        }
        default 9;
        description "PRACH compression bit width";
      }
      leaf enable-ul-static-compr-hdr {
        type boolean;
        default true;
        description "Uplink static compression header enabled flag";
      }
      leaf enable-dl-static-compr-hdr {
        type boolean;
        default true;
        description "Downlink static compression header enabled flag";
      }
    }
    list cells {
      // WARNING: no key designated; YANG list requires `key`. Use .key("...") at declaration.
      description "Sets the cell configuration on a per cell basis, overwriting the default configuration defined by cell_cfg";
      leaf t1a-max-cp-dl {
        type int64 {
          range "0..1960";
        }
        default 500;
        description "T1a maximum value for downlink Control-Plane";
      }
      leaf t1a-min-cp-dl {
        type int64 {
          range "0..1960";
        }
        default 258;
        description "T1a minimum value for downlink Control-Plane";
      }
      leaf t1a-max-cp-ul {
        type int64 {
          range "0..1960";
        }
        default 500;
        description "T1a maximum value for uplink Control-Plane";
      }
      leaf t1a-min-cp-ul {
        type int64 {
          range "0..1960";
        }
        default 285;
        description "T1a minimum value for uplink Control-Plane";
      }
      leaf t1a-max-up {
        type int64 {
          range "0..1960";
        }
        default 300;
        description "T1a maximum value for User-Plane";
      }
      leaf t1a-min-up {
        type int64 {
          range "0..1960";
        }
        default 85;
        description "T1a minimum value for User-Plane";
      }
      leaf ta4-max {
        type int64 {
          range "0..1960";
        }
        default 500;
        description "Ta4 maximum value for User-Plane";
      }
      leaf ta4-min {
        type int64 {
          range "0..1960";
        }
        default 85;
        description "Ta4 minimum value for User-Plane";
      }
      leaf is-prach-cp-enabled {
        type boolean;
        default true;
        description "PRACH Control-Plane enabled flag";
      }
      leaf ignore-ecpri-seq-id {
        type boolean;
        default false;
        description "Ignore eCPRI sequence id field value";
      }
      leaf ignore-ecpri-payload-size {
        type boolean;
        default false;
        description "Ignore eCPRI payload size field value";
      }
      leaf ignore-prach-start-symbol {
        type boolean;
        default false;
        description "Ignore the start symbol field in the PRACH U-Plane packets";
      }
      leaf log-lates-as-warnings {
        type boolean;
        default true;
        description "Log late events as warnings";
      }
      leaf warn-unreceived-ru-frames {
        type enumeration {
          enum "never";
          enum "always";
          enum "after_traffic_detection";
        }
        default "after_traffic_detection";
        description "Warn of unreceived Radio Unit frames";
      }
      leaf compr-method-ul {
        type enumeration {
          enum "none";
          enum "bfp";
          enum "bfp selective";
          enum "block scaling";
          enum "mu law";
          enum "modulation";
          enum "modulation selective";
        }
        default "bfp";
        description "Uplink compression method";
      }
      leaf compr-bitwidth-ul {
        type uint32 {
          range "1..16";
        }
        default 9;
        description "Uplink compression bit width";
      }
      leaf compr-method-dl {
        type enumeration {
          enum "none";
          enum "bfp";
          enum "bfp selective";
          enum "block scaling";
          enum "mu law";
          enum "modulation";
          enum "modulation selective";
        }
        default "bfp";
        description "Downlink compression method";
      }
      leaf compr-bitwidth-dl {
        type uint32 {
          range "1..16";
        }
        default 9;
        description "Downlink compression bit width";
      }
      leaf compr-method-prach {
        type enumeration {
          enum "none";
          enum "bfp";
          enum "bfp selective";
          enum "block scaling";
          enum "mu law";
          enum "modulation";
          enum "modulation selective";
        }
        default "bfp";
        description "PRACH compression method";
      }
      leaf compr-bitwidth-prach {
        type uint32 {
          range "1..16";
        }
        default 9;
        description "PRACH compression bit width";
      }
      leaf enable-ul-static-compr-hdr {
        type boolean;
        default true;
        description "Uplink static compression header enabled flag";
      }
      leaf enable-dl-static-compr-hdr {
        type boolean;
        default true;
        description "Downlink static compression header enabled flag";
      }
      leaf network-interface {
        type string;
        default "enp1s0f0";
        description "Network interface name for raw sockets. PCIe (or other bus) port identifier when using DPDK";
      }
      leaf enable-promiscuous {
        type boolean;
        default false;
        description "Promiscuous mode flag";
      }
      leaf check-link-status {
        type boolean;
        default false;
        description "Ethernet link status checking flag";
      }
      leaf ru-mac-addr {
        type string;
        default "70:b3:d5:e1:5b:06";
        description "Radio Unit MAC address";
      }
      leaf du-mac-addr {
        type string;
        default "00:11:22:33:00:77";
        description "Distributed Unit MAC address";
      }
      leaf vlan-tag-cp {
        type uint16 {
          range "1..4094";
        }
        description "C-Plane VLAN identifier";
      }
      leaf vlan-tag-up {
        type uint16 {
          range "1..4094";
        }
        description "U-Plane VLAN identifier";
      }
      leaf vlan-pcp-cp {
        type uint8 {
          range "0..7";
        }
        description "C-Plane VLAN PCP (requires --vlan_tag_cp to be set as well)";
      }
      leaf vlan-pcp-up {
        type uint8 {
          range "0..7";
        }
        description "U-Plane VLAN PCP (requires --vlan_tag_up to be set as well)";
      }
      leaf-list prach-port-id {
        type uint32;
        description "RU PRACH port identifier";
      }
      leaf-list dl-port-id {
        type uint32;
        description "RU downlink port identifier";
      }
      leaf-list ul-port-id {
        type uint32;
        description "RU uplink port identifier";
      }
    }
  }
  container ru-sdr {
    description "SDR Radio Unit configuration";
    leaf srate {
      type decimal64 {
        fraction-digits 6;
      }
      default 61.44;
      description "Sample rate in MHz";
    }
    leaf device-driver {
      type string;
      default "uhd";
      description "Device driver name";
    }
    leaf device-args {
      type string;
      default "";
      description "Optional device arguments";
    }
    leaf tx-gain {
      type decimal64 {
        fraction-digits 6;
      }
      default 50;
      description "Transmit gain in decibels";
    }
    leaf rx-gain {
      type decimal64 {
        fraction-digits 6;
      }
      default 60;
      description "Receive gain in decibels";
    }
    leaf freq-offset {
      type decimal64 {
        fraction-digits 6;
      }
      default 0;
      description "Center frequency offset in hertz";
    }
    leaf clock-ppm {
      type decimal64 {
        fraction-digits 6;
      }
      default 0;
      description "Clock calibration in PPM.";
    }
    leaf lo-offset {
      type decimal64 {
        fraction-digits 6;
      }
      default 0;
      description "LO frequency offset in MHz";
    }
    leaf clock {
      type string;
      default "default";
      description "Clock source";
    }
    leaf sync {
      type string;
      default "default";
      description "Time synchronization source";
    }
    leaf otw-format {
      type string;
      default "default";
      description "Over-the-wire format";
    }
    leaf time-alignment-calibration {
      type string;
      default "auto";
      description "Rx to Tx radio time alignment calibration in samples.
Positive values reduce the RF transmission delay with respect
to the RF reception, while negative values increase it (a signed integer or the sentinel \"auto\" (skip calibration))";
    }
    leaf dl-freq-Hz {
      type decimal64 {
        fraction-digits 6;
      }
      description "Downlink frequency in Hz. If present, it overrides the one derived by DL ARFCN and NR Band.";
    }
    leaf ul-freq-Hz {
      type decimal64 {
        fraction-digits 6;
      }
      description "Uplink frequency in Hz. If present, it overrides the one derived by UL ARFCN and NR Band.";
    }
    container amplitude-control {
      description "Amplitude control parameters";
      leaf tx-gain-backoff {
        type decimal64 {
          fraction-digits 6;
        }
        default 12;
        description "Gain back-off to accommodate the signal PAPR in decibels";
      }
      leaf enable-clipping {
        type boolean;
        default false;
        description "Signal clipping";
      }
      leaf ceiling {
        type decimal64 {
          fraction-digits 6;
        }
        default -0.1;
        description "Clipping ceiling referenced to full scale";
      }
    }
    container expert-cfg {
      description "Generic Radio Unit expert configuration";
      leaf low-phy-dl-throttling {
        type decimal64 {
          fraction-digits 6;
        }
        default 0;
        description "System time-based throttling.
Determines a minimum baseband processor period time between downlink packets. It is expressed as a 
fraction of the time equivalent to the number of samples in the baseband buffer. Set to 0.9 to ensure 
that the downlink packets are processed with a minimum period of 90% of the buffer duration.
Set to zero to disable this feature.";
      }
      leaf tx-mode {
        type enumeration {
          enum "continuous";
          enum "discontinuous";
          enum "same-port";
        }
        default "continuous";
        description "Selects a radio transmission mode. Discontinuous modes are not supported by all radios.
  continuous:    the TX chain is always active.
  discontinuous: the transmitter stops when there is no data to transmit.
  same-port:     the radio transmits and receives from the same antenna port.
";
      }
      leaf power-ramping-time-us {
        type decimal64 {
          fraction-digits 6;
        }
        default 0;
        description "Specifies the power ramping time in microseconds, it proactively initiates the transmission and 
mitigates transient effects.";
      }
    }
  }
  container ru-dummy {
    description "Dummy Radio Unit configuration";
    leaf dl-processing-delay {
      type uint32;
      default 1;
      description "DL processing processing delay in slots";
    }
    leaf time-scaling {
      type decimal64 {
        fraction-digits 6;
        range "0..max";
      }
      default 1;
      description "Time scaling factor applied to the slot duration. Must be greater than zero. A value greater than one slows down the RU, while a value between zero and one speeds it up.";
    }
  }
}
